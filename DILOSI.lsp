;;; ================================================================
;;; DILOSI.LSP v1.3 - HEXIS CAD Tools / BRB DEVELOPMENT MON. I.K.E.
;;; Δηλώσεις τοπογραφικού διαγράμματος:
;;;   - Δήλωση Μηχανικού Ν.651/77 & Ν.1337/83 (εντός / εκτός σχεδίου)
;;;   - Δήλωση Ιδιοκτήτη Ν.4030/2011 (θέση - όρια - ανάθεση)
;;; Διαβάζει αυτόματα την ιδιοκτησία και τις ονομασίες κορυφών από το layer TOPO_PROP
;;; Εντολές: DILOSI  (wizard με tabs)
;;;          DILOSI4030 (μόνο η δήλωση ιδιοκτήτη)
;;;          DILOSISET  (γρήγορη αλλαγή κλίμακας/ύψους)
;;; ΠΡΟΣΟΧΗ: το αρχείο είναι σε WINDOWS-1253 (ελληνικά DCL).
;;;          ΜΗΝ το αποθηκεύσετε ως UTF-8.
;;; ================================================================
(vl-load-com)

;; ---------------- globals ----------------
(if (null *DL*) (setq *DL* nil))
(defun dl:get (k / a) (if (setq a (assoc k *DL*)) (cdr a) ""))
(defun dl:geti (k) (atoi (dl:get k)))
(defun dl:set (k v) (setq *DL* (subst (cons k v) (assoc k *DL*) *DL*))
  (if (null (assoc k *DL*)) (setq *DL* (cons (cons k v) *DL*))) v)
(defun dl:nz (s) (and s (/= s "") (/= s " ")))

(defun dl:init ( / d)
  (setq d (list
    (cons "eidos" "0") (cons "kor" "") (cons "emb" "") (cons "thesi" "")
    (cons "dk" "") (cons "dimos" "") (cons "pe" "") (cons "ot" "") (cons "kaek" "")
    (cons "pos" "3") (cons "gps" "0") (cons "gpsfek" "") (cons "zoe" "0") (cons "zoefek" "")
    (cons "parad" "0") (cons "fekrym" "") (cons "fekoron" "") (cons "oikfek" "")
    (cons "artio" "1") (cons "vasi" "0") (cons "oik" "1") (cons "artemb" "")
    (cons "pros" "") (cons "odos" "2") (cons "katat" "1") (cons "katdate" "")
    (cons "n1337" "0") (cons "eisgi" "0") (cons "eisxr" "0") (cons "praxi" "2")
    (cons "n2242" "0") (cons "ktim" "1") (cons "aig" "0") (cons "aigd" "")
    (cons "rema" "0") (cons "remad" "") (cons "dasos" "0") (cons "arxaio" "0")
    (cons "dei" "0") (cons "aerio" "0")
    (cons "mix" "") (cons "eid" "") (cons "tee" "") (cons "idio" "") (cons "pat" "")
    (cons "afm" "") (cons "klim" "500") (cons "mon" "0") (cons "hmm" "2.5")
    (cons "wmm" "90") (cons "d651" "1") (cons "d4030" "1") (cons "hmer" "")
  ))
  (if (null *DL*) (setq *DL* d)
    (foreach p d (if (null (assoc (car p) *DL*)) (setq *DL* (cons p *DL*))))
  )
  ;; γέφυρα με OROIDOM: αν έχει τρέξει, παίρνουμε ΟΤ / περιοχή
  (if *BRB-OROI*
    (progn
      (if (and (assoc "OT" *BRB-OROI*) (not (dl:nz (dl:get "ot"))))
          (dl:set "ot" (cdr (assoc "OT" *BRB-OROI*))))
      (if (and (assoc "PERIOXI" *BRB-OROI*) (not (dl:nz (dl:get "thesi"))))
          (dl:set "thesi" (cdr (assoc "PERIOXI" *BRB-OROI*))))
      (if (and (assoc "FEK" *BRB-OROI*) (not (dl:nz (dl:get "fekoron"))))
          (dl:set "fekoron" (cdr (assoc "FEK" *BRB-OROI*))))
    ))
  (if (not (dl:nz (dl:get "hmer"))) (dl:set "hmer" (dl:today)))
  ;; αυτόματη ανάγνωση ιδιοκτησίας από το layer TOPO_PROP
  (if (not (dl:nz (dl:get "kor"))) (dl:prop-info T))
  (princ))

(defun dl:today ( / d)
  (setq d (rtos (getvar "CDATE") 2 6))
  (strcat (substr d 7 2) "/" (substr d 5 2) "/" (substr d 1 4)))

;; ---------------- λίστες ----------------
(setq *DL-EIDOS* (list "\\U+039F\\U+0399\\U+039A\\U+039F\\U+03A0\\U+0395\\U+0394\\U+039F" "\\U+0391\\U+0393\\U+03A1\\U+039F\\U+03A4\\U+0395\\U+039C\\U+0391\\U+03A7\\U+0399\\U+039F" "\\U+0393\\U+0397\\U+03A0\\U+0395\\U+0394\\U+039F" "\\U+039A\\U+039B\\U+0397\\U+03A1\\U+039F\\U+03A4\\U+0395\\U+039C\\U+0391\\U+03A7\\U+0399\\U+039F" "\\U+0391\\U+039A\\U+0399\\U+039D\\U+0397\\U+03A4\\U+039F"))
(setq *DL-EIDOSG* (list "\\U+03BF\\U+03B9\\U+03BA\\U+03CC\\U+03C0\\U+03B5\\U+03B4\\U+03BF" "\\U+03B1\\U+03B3\\U+03C1\\U+03BF\\U+03C4\\U+03B5\\U+03BC\\U+03AC\\U+03C7\\U+03B9\\U+03BF" "\\U+03B3\\U+03AE\\U+03C0\\U+03B5\\U+03B4\\U+03BF" "\\U+03BA\\U+03BB\\U+03B7\\U+03C1\\U+03BF\\U+03C4\\U+03B5\\U+03BC\\U+03AC\\U+03C7\\U+03B9\\U+03BF" "\\U+03B1\\U+03BA\\U+03AF\\U+03BD\\U+03B7\\U+03C4\\U+03BF"))
(setq *DL-ODOS* (list "\\U+03B5\\U+03B8\\U+03BD\\U+03B9\\U+03BA\\U+03AE \\U+03BF\\U+03B4\\U+03CC" "\\U+03B5\\U+03C0\\U+03B1\\U+03C1\\U+03C7\\U+03B9\\U+03B1\\U+03BA\\U+03AE \\U+03BF\\U+03B4\\U+03CC" "\\U+03B4\\U+03B7\\U+03BC\\U+03BF\\U+03C4\\U+03B9\\U+03BA\\U+03AE \\U+03BF\\U+03B4\\U+03CC" "\\U+03B1\\U+03B3\\U+03C1\\U+03BF\\U+03C4\\U+03B9\\U+03BA\\U+03AE \\U+03BF\\U+03B4\\U+03CC" "\\U+03BA\\U+03BF\\U+03B9\\U+03BD\\U+03BF\\U+03C4\\U+03B9\\U+03BA\\U+03AE \\U+03BF\\U+03B4\\U+03CC" "\\U+03B9\\U+03B4\\U+03B9\\U+03C9\\U+03C4\\U+03B9\\U+03BA\\U+03AE \\U+03BF\\U+03B4\\U+03CC" "\\U+03BA\\U+03BF\\U+03B9\\U+03BD\\U+03CC\\U+03C7\\U+03C1\\U+03B7\\U+03C3\\U+03C4\\U+03BF \\U+03C7\\U+03CE\\U+03C1\\U+03BF"))
(setq *DL-ALFA* (list "\\U+0391" "\\U+0392" "\\U+0393" "\\U+0394" "\\U+0395" "\\U+0396" "\\U+0397" "\\U+0398" "\\U+0399" "\\U+039A" "\\U+039B" "\\U+039C" "\\U+039D" "\\U+039E" "\\U+039F" "\\U+03A0" "\\U+03A1" "\\U+03A3" "\\U+03A4" "\\U+03A5" "\\U+03A6" "\\U+03A7" "\\U+03A8" "\\U+03A9"))

;; ---------------- κορυφές από το σχέδιο ----------------
(defun dl:label (i / n r)
  (setq n (length *DL-ALFA*))
  (if (< i n) (nth i *DL-ALFA*)
    (strcat (nth (rem i n) *DL-ALFA*) (itoa (/ i n)))))

(setq *DL-LAYER* "TOPO_PROP")

;; καθαρισμός mtext formatting
(defun dl:strip (s / p)
  (if (and (> (strlen s) 0) (= (substr s 1 1) "{"))
    (progn
      (setq s (vl-string-trim "{}" s))
      (if (setq p (vl-string-search ";" s)) (setq s (substr s (+ p 2))))))
  (vl-string-trim " \t" s))

;; όλα τα σημεία κορυφών μιας LWPOLYLINE, με τη σειρά
(defun dl:verts (e / d lst)
  (setq lst nil)
  (foreach d (entget e)
    (if (= (car d) 10) (setq lst (cons (cdr d) lst))))
  (reverse lst))

;; κείμενα ονομασιών στο layer, ως ((σημείο . κείμενο) ...)
(defun dl:labels (lay / ss i e d p t0 lst)
  (setq ss (ssget "_X" (list (cons 0 "TEXT,MTEXT") (cons 8 lay)
                             (cons 410 (getvar "CTAB")))))
  (setq lst nil i 0)
  (if ss
    (while (< i (sslength ss))
      (setq e (ssname ss i) d (entget e))
      (setq p (cdr (assoc 11 d)))
      (if (or (null p) (equal p (list 0.0 0.0 0.0) 1e-8)) (setq p (cdr (assoc 10 d))))
      (setq t0 (dl:strip (cdr (assoc 1 d))))
      (if (and t0 (> (strlen t0) 0) (< (strlen t0) 5))
        (setq lst (cons (cons p t0) lst)))
      (setq i (1+ i))))
  lst)

;; μέσο μήκος πλευράς (για ανοχή αντιστοίχισης)
(defun dl:avgseg (pts / n i s)
  (setq n (length pts) i 0 s 0.0)
  (while (< i (1- n))
    (setq s (+ s (distance (nth i pts) (nth (1+ i) pts))))
    (setq i (1+ i)))
  (if (> n 1) (/ s (float (1- n))) 1.0))

;; ---- η βασική: διαβάζει την ιδιοκτησία από το layer TOPO_PROP ----
;; XData ιδιοκτησίας: προαιρετικό, δεν υπάρχουν ακόμα δεδομένα -> ασφαλές κενό
(defun dl:xd-read (e) nil)

(defun dl:prop-info (silent / ss e o n i j pts txts tol best bd d nm fst used s ar)
  (setq ss (ssget "_X" (list (cons 0 "LWPOLYLINE") (cons 8 *DL-LAYER*)
                             (cons 410 (getvar "CTAB")))))
  (cond
    ((null ss)
     (if (not silent)
       (progn
         (princ (strcat "\n" "\\U+0394\\U+03B5\\U+03BD \\U+03B2\\U+03C1\\U+03AD\\U+03B8\\U+03B7\\U+03BA\\U+03B5 \\U+03C0\\U+03BF\\U+03BB\\U+03CD\\U+03B3\\U+03C9\\U+03BD\\U+03BF \\U+03C3\\U+03C4\\U+03BF layer " *DL-LAYER* " - \\U+03B5\\U+03C0\\U+03B9\\U+03BB\\U+03AD\\U+03BE\\U+03C4\\U+03B5 \\U+03C7\\U+03B5\\U+03B9\\U+03C1\\U+03BF\\U+03BA\\U+03AF\\U+03BD\\U+03B7\\U+03C4\\U+03B1: "))
         (setq e (car (entsel))))))
    ((= (sslength ss) 1) (setq e (ssname ss 0)))
    (T
     ;; πολλά πολύγωνα: κρατάμε το μεγαλύτερο, εκτός αν ο χρήστης δείξει άλλο
     (if silent
       (progn
         (setq i 0 bd -1.0)
         (while (< i (sslength ss))
           (setq o (vlax-ename->vla-object (ssname ss i)))
           (if (> (vla-get-Area o) bd)
             (setq bd (vla-get-Area o) e (ssname ss i)))
           (setq i (1+ i))))
       (progn
         (princ (strcat "\n" "\\U+0392\\U+03C1\\U+03AD\\U+03B8\\U+03B7\\U+03BA\\U+03B1\\U+03BD " (itoa (sslength ss))
                        " \\U+03C0\\U+03BF\\U+03BB\\U+03CD\\U+03B3\\U+03C9\\U+03BD\\U+03B1 \\U+03C3\\U+03C4\\U+03BF " *DL-LAYER* " - \\U+03B4\\U+03B5\\U+03AF\\U+03BE\\U+03C4\\U+03B5 \\U+03C4\\U+03BF \\U+03C3\\U+03C9\\U+03C3\\U+03C4\\U+03CC: "))
         (setq e (car (entsel)))))))
  (if (and e (= (cdr (assoc 0 (entget e))) "LWPOLYLINE"))
    (progn
      (setq o (vlax-ename->vla-object e))
      (setq ar (vla-get-Area o))
      (setq pts (dl:verts e))
      (setq n (length pts))
      (setq txts (dl:labels *DL-LAYER*))
      (setq tol (* 0.55 (dl:avgseg pts)))
      (setq used nil s "" i 0)
      (while (< i n)
        (setq best nil bd tol)
        (foreach d txts
          (if (not (member d used))
            (progn
              (setq j (distance (list (car (car d)) (cadr (car d)))
                                (list (car (nth i pts)) (cadr (nth i pts)))))
              (if (< j bd) (setq bd j best d)))))
        (if best
          (progn (setq nm (cdr best)) (setq used (cons best used)))
          (setq nm (dl:label i)))
        (setq s (strcat s (if (= i 0) "" "-") nm))
        (if (= i 0) (setq fst nm))
        (setq i (1+ i)))
      (setq s (strcat s "-" fst))
      (dl:set "kor" s)
      (dl:set "emb" (rtos ar 2 2))
      (dl:xd-read e)
      (if (not silent)
        (princ (strcat "\n" *DL-LAYER* ": " s "   |   E = " (rtos ar 2 2) " m2")))
      T)
    nil))

;; κορυφές από πίνακα συντεταγμένων (ACAD_TABLE ή μεμονωμένα TEXT)
(defun dl:table-info ( / ss e o rows i v lst txts x0 pt s)
  (princ "\n\\U+0395\\U+03C0\\U+03B9\\U+03BB\\U+03AD\\U+03BE\\U+03C4\\U+03B5 \\U+03C4\\U+03BF\\U+03BD \\U+03C0\\U+03AF\\U+03BD\\U+03B1\\U+03BA\\U+03B1 \\U+03C3\\U+03C5\\U+03BD\\U+03C4\\U+03B5\\U+03C4\\U+03B1\\U+03B3\\U+03BC\\U+03AD\\U+03BD\\U+03C9\\U+03BD (TABLE) \\U+03AE \\U+03C4\\U+03B1 \\U+03BA\\U+03B5\\U+03AF\\U+03BC\\U+03B5\\U+03BD\\U+03B1 \\U+03C4\\U+03C9\\U+03BD \\U+03BF\\U+03BD\\U+03BF\\U+03BC\\U+03B1\\U+03C3\\U+03B9\\U+03CE\\U+03BD: ")
  (setq ss (ssget))
  (setq lst nil txts nil)
  (if ss
    (progn
      (setq i 0)
      (while (< i (sslength ss))
        (setq e (ssname ss i))
        (cond
          ((= (cdr (assoc 0 (entget e))) "ACAD_TABLE")
           (setq o (vlax-ename->vla-object e) rows (vla-get-Rows o))
           (setq v 0)
           (while (< v rows)
             (setq s (vl-string-trim " \t" (vla-GetText o v 0)))
             (if (and (> (strlen s) 0) (< (strlen s) 4) (not (wcmatch s "*/*")))
               (setq lst (cons s lst)))
             (setq v (1+ v))))
          ((member (cdr (assoc 0 (entget e))) (list "TEXT" "MTEXT"))
           (setq txts (cons (cons (cdr (assoc 10 (entget e)))
                                  (vl-string-trim " \t" (cdr (assoc 1 (entget e))))) txts)))
        )
        (setq i (1+ i)))
      ;; αν μαζέψαμε TEXT: κρατάμε την αριστερότερη στήλη, ταξινόμηση κατά Y φθίνουσα
      (if (and (null lst) txts)
        (progn
          (setq x0 (apply (function min) (mapcar (function (lambda (p) (car (car p)))) txts)))
          (setq txts (vl-remove-if-not
                       (function (lambda (p) (< (abs (- (car (car p)) x0)) (* 0.15 (getvar "VIEWSIZE"))))) txts))
          (setq txts (vl-sort txts (function (lambda (a b) (> (cadr (car a)) (cadr (car b)))))))
          (foreach p txts
            (if (and (> (strlen (cdr p)) 0) (< (strlen (cdr p)) 4))
              (setq lst (cons (cdr p) lst))))
          (setq lst (reverse lst))))
      (if lst
        (progn
          (setq lst (reverse lst))
          (setq s "")
          (foreach k lst (setq s (strcat s (if (= s "") "" "-") k)))
          (setq s (strcat s "-" (car lst)))
          (dl:set "kor" s)
          (princ (strcat "\n" s)))
        (princ "\n\\U+0394\\U+03B5\\U+03BD \\U+03B2\\U+03C1\\U+03AD\\U+03B8\\U+03B7\\U+03BA\\U+03B1\\U+03BD \\U+03BF\\U+03BD\\U+03BF\\U+03BC\\U+03B1\\U+03C3\\U+03AF\\U+03B5\\U+03C2 \\U+03BA\\U+03BF\\U+03C1\\U+03C5\\U+03C6\\U+03CE\\U+03BD."))))
  (princ))

;; ---------------- DCL ----------------
(defun dl:dclfile ( / f p)
  (setq p (strcat (getvar "TEMPPREFIX") "brb_dilosi.dcl"))
  (setq f (open p "w"))
  (defun w (s) (write-line s f))
  (w "dl1 : dialog { label = \"HEXIS - ΔΗΛΩΣΕΙΣ ΤΟΠΟΓΡΑΦΙΚΟΥ  |  1. ΣΤΟΙΧΕΙΑ ΑΚΙΝΗΤΟΥ\";")
  (w "  : row { fixed_width = true;")
  (w "    : button { key = \"t1\"; label = \"[ 1.ΑΚΙΝΗΤΟ ]\"; width = 14; fixed_width = true; is_enabled = false; }")
  (w "    : button { key = \"t2\"; label = \"  2.ΘΕΣΗ  \"; width = 14; fixed_width = true; }")
  (w "    : button { key = \"t3\"; label = \"  3.ΑΡΤΙΟΤΗΤΑ  \"; width = 14; fixed_width = true; }")
  (w "    : button { key = \"t4\"; label = \"  4.ΛΟΙΠΑ  \"; width = 14; fixed_width = true; }")
  (w "    : button { key = \"t5\"; label = \"  5.ΕΞΟΔΟΣ  \"; width = 14; fixed_width = true; }")
  (w "  }")
  (w "  spacer_0;")
  (w "  : boxed_column { label = \"Ταυτότητα ακινήτου\";")
  (w "    : popup_list { key = \"eidos\"; label = \"Είδος ακινήτου :\"; width = 24; }")
  (w "    : row {")
  (w "      : edit_box { key = \"kor\"; label = \"Κορυφές (Α-Β-Γ-..) :\"; edit_width = 34; }")
  (w "    }")
  (w "    : row {")
  (w "      : button { key = \"bpoly\"; label = \"<< Ανάγνωση layer TOPO_PROP\"; width = 30; }")
  (w "      : button { key = \"btab\"; label = \"<< Από πίνακα συν/νων\"; width = 26; }")
  (w "    }")
  (w "    : edit_box { key = \"emb\"; label = \"Εμβαδόν (τ.μ.) :\"; edit_width = 16; }")
  (w "  }")
  (w "  : boxed_column { label = \"Διοικητικά\";")
  (w "    : edit_box { key = \"thesi\"; label = \"Θέση / Τοπωνύμιο :\"; edit_width = 34; }")
  (w "    : edit_box { key = \"dk\"; label = \"Δ.Κ. / Τ.Κ. :\"; edit_width = 34; }")
  (w "    : edit_box { key = \"dimos\"; label = \"Δήμος :\"; edit_width = 34; }")
  (w "    : edit_box { key = \"pe\"; label = \"Π.Ε. :\"; edit_width = 34; }")
  (w "    : row {")
  (w "      : edit_box { key = \"ot\"; label = \"Ο.Τ. :\"; edit_width = 10; }")
  (w "      : edit_box { key = \"kaek\"; label = \"ΚΑΕΚ :\"; edit_width = 22; }")
  (w "    }")
  (w "    : button { key = \"bkaek\"; label = \"<< Συμπλήρωση από ΚΑΕΚ (HEXIS-APP: όροι, ΦΕΚ, θέση)\"; width = 52; }")
  (w "  }")
  (w "  : row {")
  (w "    : button { key = \"prev\"; label = \"< Πίσω\"; width = 12; }")
  (w "    : button { key = \"next\"; label = \"Επόμενο >\"; width = 12; }")
  (w "    : button { key = \"ins\"; label = \"ΕΙΣΑΓΩΓΗ\"; width = 14; is_default = true; }")
  (w "    : button { key = \"can\"; label = \"Ακυρο\"; width = 10; is_cancel = true; }")
  (w "  }")
  (w "}")
  (w "")
  (w "dl2 : dialog { label = \"HEXIS - ΔΗΛΩΣΕΙΣ ΤΟΠΟΓΡΑΦΙΚΟΥ  |  2. ΘΕΣΗ - ΠΟΛΕΟΔΟΜΙΚΟ ΚΑΘΕΣΤΩΣ\";")
  (w "  : row { fixed_width = true;")
  (w "    : button { key = \"t1\"; label = \"  1.ΑΚΙΝΗΤΟ  \"; width = 14; fixed_width = true; }")
  (w "    : button { key = \"t2\"; label = \"[ 2.ΘΕΣΗ ]\"; width = 14; fixed_width = true; is_enabled = false; }")
  (w "    : button { key = \"t3\"; label = \"  3.ΑΡΤΙΟΤΗΤΑ  \"; width = 14; fixed_width = true; }")
  (w "    : button { key = \"t4\"; label = \"  4.ΛΟΙΠΑ  \"; width = 14; fixed_width = true; }")
  (w "    : button { key = \"t5\"; label = \"  5.ΕΞΟΔΟΣ  \"; width = 14; fixed_width = true; }")
  (w "  }")
  (w "  spacer_0;")
  (w "  : boxed_radio_column { key = \"pos\"; label = \"Θέση ως προς το σχέδιο\";")
  (w "    : radio_button { key = \"p0\"; label = \"Εντός εγκεκριμένου ρυμοτομικού σχεδίου\"; }")
  (w "    : radio_button { key = \"p1\"; label = \"Εντός ορίων οικισμού προϋφισταμένου του 1923\"; }")
  (w "    : radio_button { key = \"p2\"; label = \"Εντός ορίων οικισμού < 2.000 κατ. (οριοθετημένου)\"; }")
  (w "    : radio_button { key = \"p3\"; label = \"Εκτός σχεδίου και εκτός ορίων οικισμού\"; }")
  (w "  }")
  (w "  : boxed_column { label = \"Θεσμικό πλαίσιο περιοχής\";")
  (w "    : row {")
  (w "      : toggle { key = \"gps\"; label = \"Εντός ΓΠΣ / ΣΧΟΟΑΠ / ΤΠΣ\"; }")
  (w "      : edit_box { key = \"gpsfek\"; label = \"ΦΕΚ :\"; edit_width = 20; }")
  (w "    }")
  (w "    : row {")
  (w "      : toggle { key = \"zoe\"; label = \"Εντός ΖΟΕ / ζώνης ειδικών χρήσεων\"; }")
  (w "      : edit_box { key = \"zoefek\"; label = \"ΦΕΚ :\"; edit_width = 20; }")
  (w "    }")
  (w "    : toggle { key = \"parad\"; label = \"Παραδοσιακός οικισμός / ιστορικός τόπος\"; }")
  (w "    : edit_box { key = \"fekrym\"; label = \"ΦΕΚ ρυμοτομικού :\"; edit_width = 24; }")
  (w "    : edit_box { key = \"fekoron\"; label = \"ΦΕΚ όρων δόμησης :\"; edit_width = 24; }")
  (w "    : edit_box { key = \"oikfek\"; label = \"ΦΕΚ ορίων οικισμού :\"; edit_width = 24; }")
  (w "  }")
  (w "  : text { label = \"Οι όροι δόμησης μπαίνουν με την εντολή OROIDOM (ξεχωριστός πίνακας).\"; }")
  (w "  : row {")
  (w "    : button { key = \"prev\"; label = \"< Πίσω\"; width = 12; }")
  (w "    : button { key = \"next\"; label = \"Επόμενο >\"; width = 12; }")
  (w "    : button { key = \"ins\"; label = \"ΕΙΣΑΓΩΓΗ\"; width = 14; is_default = true; }")
  (w "    : button { key = \"can\"; label = \"Ακυρο\"; width = 10; is_cancel = true; }")
  (w "  }")
  (w "}")
  (w "")
  (w "dl3 : dialog { label = \"HEXIS - ΔΗΛΩΣΕΙΣ ΤΟΠΟΓΡΑΦΙΚΟΥ  |  3. ΑΡΤΙΟΤΗΤΑ - ΟΙΚΟΔΟΜΗΣΙΜΟΤΗΤΑ\";")
  (w "  : row { fixed_width = true;")
  (w "    : button { key = \"t1\"; label = \"  1.ΑΚΙΝΗΤΟ  \"; width = 14; fixed_width = true; }")
  (w "    : button { key = \"t2\"; label = \"  2.ΘΕΣΗ  \"; width = 14; fixed_width = true; }")
  (w "    : button { key = \"t3\"; label = \"[ 3.ΑΡΤΙΟΤΗΤΑ ]\"; width = 14; fixed_width = true; is_enabled = false; }")
  (w "    : button { key = \"t4\"; label = \"  4.ΛΟΙΠΑ  \"; width = 14; fixed_width = true; }")
  (w "    : button { key = \"t5\"; label = \"  5.ΕΞΟΔΟΣ  \"; width = 14; fixed_width = true; }")
  (w "  }")
  (w "  spacer_0;")
  (w "  : boxed_radio_row { key = \"artio\"; label = \"Αρτιότητα\";")
  (w "    : radio_button { key = \"a1\"; label = \"ΑΡΤΙΟ\"; }")
  (w "    : radio_button { key = \"a0\"; label = \"ΜΗ ΑΡΤΙΟ\"; }")
  (w "  }")
  (w "  : boxed_column { label = \"Βάση αρτιότητας\";")
  (w "    : popup_list { key = \"vasi\"; label = \"Κρίνεται :\"; width = 40; }")
  (w "    : edit_box { key = \"artemb\"; label = \"Ελάχ. εμβαδόν αρτιότητας (τ.μ.) :\"; edit_width = 12; }")
  (w "    : toggle { key = \"oik\"; label = \"ΟΙΚΟΔΟΜΗΣΙΜΟ\"; }")
  (w "  }")
  (w "  : boxed_column { label = \"Πρόσωπο - Κατάτμηση\";")
  (w "    : row {")
  (w "      : edit_box { key = \"pros\"; label = \"Πρόσωπο (μ.) :\"; edit_width = 10; }")
  (w "      : popup_list { key = \"odos\"; label = \"σε :\"; width = 22; }")
  (w "    }")
  (w "    : row {")
  (w "      : toggle { key = \"katat\"; label = \"Δεν προήλθε από κατάτμηση μετά την\"; }")
  (w "      : edit_box { key = \"katdate\"; label = \"\"; edit_width = 14; }")
  (w "    }")
  (w "  }")
  (w "  : row {")
  (w "    : button { key = \"prev\"; label = \"< Πίσω\"; width = 12; }")
  (w "    : button { key = \"next\"; label = \"Επόμενο >\"; width = 12; }")
  (w "    : button { key = \"ins\"; label = \"ΕΙΣΑΓΩΓΗ\"; width = 14; is_default = true; }")
  (w "    : button { key = \"can\"; label = \"Ακυρο\"; width = 10; is_cancel = true; }")
  (w "  }")
  (w "}")
  (w "")
  (w "dl4 : dialog { label = \"HEXIS - ΔΗΛΩΣΕΙΣ ΤΟΠΟΓΡΑΦΙΚΟΥ  |  4. Ν.1337/83 ΚΑΙ ΛΟΙΠΕΣ ΔΕΣΜΕΥΣΕΙΣ\";")
  (w "  : row { fixed_width = true;")
  (w "    : button { key = \"t1\"; label = \"  1.ΑΚΙΝΗΤΟ  \"; width = 14; fixed_width = true; }")
  (w "    : button { key = \"t2\"; label = \"  2.ΘΕΣΗ  \"; width = 14; fixed_width = true; }")
  (w "    : button { key = \"t3\"; label = \"  3.ΑΡΤΙΟΤΗΤΑ  \"; width = 14; fixed_width = true; }")
  (w "    : button { key = \"t4\"; label = \"[ 4.ΛΟΙΠΑ ]\"; width = 14; fixed_width = true; is_enabled = false; }")
  (w "    : button { key = \"t5\"; label = \"  5.ΕΞΟΔΟΣ  \"; width = 14; fixed_width = true; }")
  (w "  }")
  (w "  spacer_0;")
  (w "  : boxed_column { label = \"Ν.1337/83 - Εισφορές\";")
  (w "    : toggle { key = \"n1337\"; label = \"Υπάγεται στις διατάξεις του Ν.1337/83\"; }")
  (w "    : row {")
  (w "      : toggle { key = \"eisgi\"; label = \"Οφείλει εισφορά σε γη\"; }")
  (w "      : toggle { key = \"eisxr\"; label = \"Οφείλει εισφορά σε χρήμα\"; }")
  (w "    }")
  (w "    : popup_list { key = \"praxi\"; label = \"Πράξη εφαρμογής :\"; width = 26; }")
  (w "  }")
  (w "  : boxed_column { label = \"Λοιπές αναφορές\";")
  (w "    : toggle { key = \"n2242\"; label = \"Εμπίπτει στις διατάξεις του Ν.2242/94\"; }")
  (w "    : toggle { key = \"ktim\"; label = \"Σε περιοχή λειτουργίας Εθνικού Κτηματολογίου (Ν.2308/95)\"; }")
  (w "    : row {")
  (w "      : toggle { key = \"aig\"; label = \"Εντός ζώνης αιγιαλού/παραλίας\"; }")
  (w "      : edit_box { key = \"aigd\"; label = \"Απόσταση από ακτή (μ.) :\"; edit_width = 10; }")
  (w "    }")
  (w "    : row {")
  (w "      : toggle { key = \"rema\"; label = \"Γειτνιάζει με ρέμα\"; }")
  (w "      : edit_box { key = \"remad\"; label = \"Απόσταση (μ.) :\"; edit_width = 10; }")
  (w "    }")
  (w "    : toggle { key = \"dasos\"; label = \"Εμπίπτει σε δασική έκταση / αναρτημένο δασικό χάρτη\"; }")
  (w "    : toggle { key = \"arxaio\"; label = \"Εμπίπτει σε ζώνη αρχαιολογικού ενδιαφέροντος\"; }")
  (w "    : toggle { key = \"dei\"; label = \"Διέρχεται εναέρια γραμμή ΔΕΗ υψηλής τάσης\"; }")
  (w "    : toggle { key = \"aerio\"; label = \"Διέρχεται αγωγός φυσικού αερίου\"; }")
  (w "  }")
  (w "  : row {")
  (w "    : button { key = \"prev\"; label = \"< Πίσω\"; width = 12; }")
  (w "    : button { key = \"next\"; label = \"Επόμενο >\"; width = 12; }")
  (w "    : button { key = \"ins\"; label = \"ΕΙΣΑΓΩΓΗ\"; width = 14; is_default = true; }")
  (w "    : button { key = \"can\"; label = \"Ακυρο\"; width = 10; is_cancel = true; }")
  (w "  }")
  (w "}")
  (w "")
  (w "dl5 : dialog { label = \"HEXIS - ΔΗΛΩΣΕΙΣ ΤΟΠΟΓΡΑΦΙΚΟΥ  |  5. ΥΠΟΓΡΑΦΕΣ - ΕΞΟΔΟΣ ΣΧΕΔΙΟΥ\";")
  (w "  : row { fixed_width = true;")
  (w "    : button { key = \"t1\"; label = \"  1.ΑΚΙΝΗΤΟ  \"; width = 14; fixed_width = true; }")
  (w "    : button { key = \"t2\"; label = \"  2.ΘΕΣΗ  \"; width = 14; fixed_width = true; }")
  (w "    : button { key = \"t3\"; label = \"  3.ΑΡΤΙΟΤΗΤΑ  \"; width = 14; fixed_width = true; }")
  (w "    : button { key = \"t4\"; label = \"  4.ΛΟΙΠΑ  \"; width = 14; fixed_width = true; }")
  (w "    : button { key = \"t5\"; label = \"[ 5.ΕΞΟΔΟΣ ]\"; width = 14; fixed_width = true; is_enabled = false; }")
  (w "  }")
  (w "  spacer_0;")
  (w "  : boxed_column { label = \"Συντάκτης\";")
  (w "    : edit_box { key = \"mix\"; label = \"Ονοματεπώνυμο μηχανικού :\"; edit_width = 30; }")
  (w "    : edit_box { key = \"eid\"; label = \"Ειδικότητα :\"; edit_width = 30; }")
  (w "    : edit_box { key = \"tee\"; label = \"Α.Μ. ΤΕΕ :\"; edit_width = 14; }")
  (w "  }")
  (w "  : boxed_column { label = \"Ιδιοκτήτης (για τη δήλωση Ν.4030/2011)\";")
  (w "    : edit_box { key = \"idio\"; label = \"Ονοματεπώνυμο :\"; edit_width = 30; }")
  (w "    : row {")
  (w "      : edit_box { key = \"pat\"; label = \"Πατρώνυμο :\"; edit_width = 16; }")
  (w "      : edit_box { key = \"afm\"; label = \"ΑΦΜ :\"; edit_width = 14; }")
  (w "    }")
  (w "  }")
  (w "  : boxed_column { label = \"Εξοδος στο σχέδιο\";")
  (w "    : row {")
  (w "      : edit_box { key = \"klim\"; label = \"Κλίμακα  1 :\"; edit_width = 8; }")
  (w "      : edit_box { key = \"hmm\"; label = \"Υψος γραμμάτων (mm χαρτιού) :\"; edit_width = 6; }")
  (w "      : edit_box { key = \"wmm\"; label = \"Πλάτος πλαισίου (mm) :\"; edit_width = 6; }")
  (w "    }")
  (w "    : radio_row { key = \"mon\"; label = \"Μονάδες σχεδίου\";")
  (w "      : radio_button { key = \"m0\"; label = \"μέτρα\"; }")
  (w "      : radio_button { key = \"m1\"; label = \"χιλιοστά\"; }")
  (w "    }")
  (w "    : row {")
  (w "      : toggle { key = \"d651\"; label = \"Δήλωση Ν.651/77 & Ν.1337/83\"; }")
  (w "      : toggle { key = \"d4030\"; label = \"Δήλωση ιδιοκτήτη Ν.4030/2011\"; }")
  (w "    }")
  (w "    : edit_box { key = \"hmer\"; label = \"Ημερομηνία :\"; edit_width = 14; }")
  (w "  }")
  (w "  : row {")
  (w "    : button { key = \"prev\"; label = \"< Πίσω\"; width = 12; }")
  (w "    : button { key = \"next\"; label = \"Επόμενο >\"; width = 12; }")
  (w "    : button { key = \"ins\"; label = \"ΕΙΣΑΓΩΓΗ\"; width = 14; is_default = true; }")
  (w "    : button { key = \"can\"; label = \"Ακυρο\"; width = 10; is_cancel = true; }")
  (w "  }")
  (w "}")
  (w "")
  (close f)
  p)

;; ---------------- helpers διαλόγου ----------------
(defun dl:fill (keys) (foreach k keys (set_tile k (dl:get k))))
(defun dl:grab (keys) (foreach k keys (dl:set k (get_tile k))))
(defun dl:tabs (n / i)
  (setq i 1)
  (while (< i 6)
    (if (/= i n) (action_tile (strcat "t" (itoa i))
      (strcat "(dl:grab *KEYS*)(done_dialog " (itoa (+ 10 i)) ")")))
    (setq i (1+ i))))
(defun dl:foot (n)
  (action_tile "prev" (strcat "(dl:grab *KEYS*)(done_dialog " (itoa (+ 10 (max 1 (1- n)))) ")"))
  (action_tile "next" (strcat "(dl:grab *KEYS*)(done_dialog " (itoa (+ 10 (min 5 (1+ n)))) ")"))
  (action_tile "ins"  "(dl:grab *KEYS*)(done_dialog 1)")
  (action_tile "can"  "(done_dialog 0)"))


;; ---------------- \U+03C3\U+03C5\U+03BC\U+03C0\U+03BB\U+03AE\U+03C1\U+03C9\U+03C3\U+03B7 \U+03B1\U+03C0\U+03CC \U+039A\U+0391\U+0395\U+039A (HEXIS-APP) ----------------
(defun dl:from-kaek ( / d k f2 st)
  (if (null hx:oroi)
        (if (findfile "HEXISNET.lsp") (load (findfile "HEXISNET.lsp"))
          (if (findfile "HEXISNET_ProgeCAD.lsp") (load (findfile "HEXISNET_ProgeCAD.lsp")))))
      (if (null hx:oroi)
        (progn (princ (strcat "\n" "\U+0394\U+03B5\U+03BD \U+03B2\U+03C1\U+03AD\U+03B8\U+03B7\U+03BA\U+03B5 \U+03C4\U+03BF HEXISNET.lsp \U+2014 \U+03C6\U+03CC\U+03C1\U+03C4\U+03C9\U+03C3\U+03AD \U+03C4\U+03BF \U+03BC\U+03B5 APPLOAD.")) (setq d 'skip)))
  (setq k (dl:get "kaek"))
  (if (and hx:oroi (/= d 'skip))
    (if (not (dl:nz k))
      (alert "\U+0393\U+03C1\U+03AC\U+03C8\U+03B5 \U+03C0\U+03C1\U+03CE\U+03C4\U+03B1 \U+03C4\U+03BF \U+039A\U+0391\U+0395\U+039A \U+03C3\U+03C4\U+03B7 \U+03C3\U+03B5\U+03BB\U+03AF\U+03B4\U+03B1 1.")
      (if (setq d (hx:oroi k))
        (progn
          (defun f2 (key fld) (if (and (/= (hx:v d key) "") (not (dl:nz (dl:get fld)))) (dl:set fld (hx:v d key))))
          (f2 "EMBADON" "emb") (f2 "DIMOS" "dimos") (f2 "OT" "ot") (f2 "OIKISMOS" "thesi")
          (setq st (hx:v d "KATASTASI"))
          (dl:set "pos" (cond ((= st "sxedio") "0") ((= st "oikismos") "2") (T "3")))
          (if (= (hx:v d "GPS") "1") (progn (dl:set "gps" "1") (f2 "FEK_GPS" "gpsfek")))
          (if (= (hx:v d "ZOE") "1") (progn (dl:set "zoe" "1") (f2 "FEK_ZOE" "zoefek")))
          (f2 "FEK_SXEDIO" "fekrym") (f2 "FEK_OROI" "fekoron") (f2 "FEK_OIKISMOU" "oikfek")
          (f2 "ART_EMB" "artemb") (f2 "PROSOPO" "pros")
          (cond ((= (hx:v d "ARTIO") "1") (dl:set "artio" "1")) ((= (hx:v d "ARTIO") "0") (dl:set "artio" "0")))
          (if (= (hx:v d "ARXAIO") "1") (dl:set "arxaio" "1"))
          (if (= (hx:v d "REMA") "1") (dl:set "rema" "1"))
          (alert (strcat "HEXIS-APP \U+2014 \U+039A\U+0391\U+0395\U+039A " (hx:v d "KAEK") "\n\n"
                         (hx:v d "KATASTASI_TXT")
                         (if (/= (hx:v d "MAX_DOMISI") "") (strcat "\n\U+039C\U+03AD\U+03B3\U+03B9\U+03C3\U+03C4\U+03B7 \U+03B4\U+03CC\U+03BC\U+03B7\U+03C3\U+03B7: " (hx:v d "MAX_DOMISI") " \U+03C4.\U+03BC. \U+00B7 \U+03A3.\U+0391.\U+039F. " (hx:v d "SAO")) "")
                         "\n\n\U+03A3\U+03C5\U+03BC\U+03C0\U+03BB\U+03B7\U+03C1\U+03CE\U+03B8\U+03B7\U+03BA\U+03B1\U+03BD: \U+03B8\U+03AD\U+03C3\U+03B7, \U+03A6\U+0395\U+039A, \U+03B1\U+03C1\U+03C4\U+03B9\U+03CC\U+03C4\U+03B7\U+03C4\U+03B1, \U+03C0\U+03C1\U+03CC\U+03C3\U+03C9\U+03C0\U+03BF \U+03BA\U+03B1\U+03B9 \U+03C4\U+03B1 \U+03BA\U+03B5\U+03BD\U+03AC \U+03C0\U+03B5\U+03B4\U+03AF\U+03B1."
                         "\n\U+0388\U+03BB\U+03B5\U+03B3\U+03BE\U+03B5 \U+03C4\U+03B9\U+03C2 \U+03C3\U+03B5\U+03BB\U+03AF\U+03B4\U+03B5\U+03C2 2-4 \U+03C0\U+03C1\U+03B9\U+03BD \U+03C4\U+03B7\U+03BD \U+03B5\U+03B9\U+03C3\U+03B1\U+03B3\U+03C9\U+03B3\U+03AE."))))))
  (princ))

(defun dl:dialog ( / dcl pg res id)
  (dl:init)
  (setq dcl (dl:dclfile))
  (setq pg 1 res 99)
  (while (> pg 0)
    (setq id (load_dialog dcl))
    (if (not (new_dialog (strcat "dl" (itoa pg)) id)) (progn (setq pg 0 res 0)))
    (if (> pg 0)
      (progn
        (cond
          ((= pg 1)
           (setq *KEYS* (list "kor" "emb" "thesi" "dk" "dimos" "pe" "ot" "kaek"))
           (start_list "eidos") (mapcar (function add_list) *DL-EIDOS*) (end_list)
           (set_tile "eidos" (dl:get "eidos"))
           (dl:fill *KEYS*)
           (action_tile "eidos" "(dl:set \"eidos\" $value)")
           (action_tile "bpoly" "(dl:grab *KEYS*)(done_dialog 21)")
           (action_tile "btab"  "(dl:grab *KEYS*)(done_dialog 22)")
           (action_tile "bkaek" "(dl:grab *KEYS*)(done_dialog 23)"))
          ((= pg 2)
           (setq *KEYS* (list "gps" "gpsfek" "zoe" "zoefek" "parad" "fekrym" "fekoron" "oikfek"))
           (set_tile (strcat "p" (dl:get "pos")) "1")
           (dl:fill *KEYS*)
           (action_tile "pos" "(dl:set \"pos\" (substr $value 2))"))
          ((= pg 3)
           (setq *KEYS* (list "artemb" "oik" "pros" "katat" "katdate"))
           (start_list "vasi") (mapcar (function add_list) *DL-VASI*) (end_list)
           (set_tile "vasi" (dl:get "vasi"))
           (start_list "odos") (mapcar (function add_list) *DL-ODOS*) (end_list)
           (set_tile "odos" (dl:get "odos"))
           (set_tile (strcat "a" (dl:get "artio")) "1")
           (dl:fill *KEYS*)
           (action_tile "vasi" "(dl:set \"vasi\" $value)")
           (action_tile "odos" "(dl:set \"odos\" $value)")
           (action_tile "artio" "(dl:set \"artio\" (substr $value 2))"))
          ((= pg 4)
           (setq *KEYS* (list "n1337" "eisgi" "eisxr" "n2242" "ktim" "aig" "aigd"
                              "rema" "remad" "dasos" "arxaio" "dei" "aerio"))
           (start_list "praxi") (mapcar (function add_list) *DL-PRAXI*) (end_list)
           (set_tile "praxi" (dl:get "praxi"))
           (dl:fill *KEYS*)
           (action_tile "praxi" "(dl:set \"praxi\" $value)"))
          ((= pg 5)
           (setq *KEYS* (list "mix" "eid" "tee" "idio" "pat" "afm" "klim" "hmm" "wmm"
                              "d651" "d4030" "hmer"))
           (set_tile (strcat "m" (dl:get "mon")) "1")
           (dl:fill *KEYS*)
           (action_tile "mon" "(dl:set \"mon\" (substr $value 2))"))
        )
        (dl:tabs pg)
        (dl:foot pg)
        (setq res (start_dialog))
        (unload_dialog id)
        (cond
          ((= res 0) (setq pg 0))
          ((= res 1) (setq pg 0))
          ((= res 21) (dl:prop-info nil) (setq pg 1))
          ((= res 22) (dl:table-info) (setq pg 1))
          ((= res 23) (dl:from-kaek) (setq pg 1))
          ((and (> res 10) (< res 16)) (setq pg (- res 10)))
          (T (setq pg 0))))))
  res)

(setq *DL-VASI* (list "\\U+03BA\\U+03B1\\U+03C4\\U+03AC \\U+03BA\\U+03B1\\U+03BD\\U+03CC\\U+03BD\\U+03B1" "\\U+03BA\\U+03B1\\U+03C4\\U+03AC \\U+03C0\\U+03B1\\U+03C1\\U+03AD\\U+03BA\\U+03BA\\U+03BB\\U+03B9\\U+03C3\\U+03B7" "\\U+03BC\\U+03B5 \\U+03C4\\U+03BF \\U+03AC\\U+03C1\\U+03B8\\U+03C1\\U+03BF 25 \\U+03C4\\U+03BF\\U+03C5 \\U+039D.1337/83" "\\U+03C9\\U+03C2 \\U+03C0\\U+03C1\\U+03BF\\U+03CB\\U+03C6\\U+03B9\\U+03C3\\U+03C4\\U+03AC\\U+03BC\\U+03B5\\U+03BD\\U+03BF \\U+03C4\\U+03BF\\U+03C5 1923" "\\U+03BC\\U+03B5 \\U+03B8\\U+03B5\\U+03C9\\U+03C1\\U+03B7\\U+03C4\\U+03B9\\U+03BA\\U+03AE \\U+03BC\\U+03B5\\U+03C3\\U+03BF\\U+03C4\\U+03BF\\U+03B9\\U+03C7\\U+03AF\\U+03B1 (\\U+039D.\\U+0394. 690/1948)" "\\U+03C9\\U+03C2 \\U+03C4\\U+03C5\\U+03C6\\U+03BB\\U+03CC - \\U+03BC\\U+03B7 \\U+03BF\\U+03B9\\U+03BA\\U+03BF\\U+03B4\\U+03BF\\U+03BC\\U+03AE\\U+03C3\\U+03B9\\U+03BC\\U+03BF"))
(setq *DL-PRAXI* (list "\\U+03B4\\U+03B5\\U+03BD \\U+03B1\\U+03C0\\U+03B1\\U+03B9\\U+03C4\\U+03B5\\U+03AF\\U+03C4\\U+03B1\\U+03B9" "\\U+03BA\\U+03C5\\U+03C1\\U+03C9\\U+03BC\\U+03AD\\U+03BD\\U+03B7" "\\U+03BC\\U+03B7 \\U+03BA\\U+03C5\\U+03C1\\U+03C9\\U+03BC\\U+03AD\\U+03BD\\U+03B7" "\\U+03C3\\U+03B5 \\U+03B5\\U+03BE\\U+03AD\\U+03BB\\U+03B9\\U+03BE\\U+03B7"))

;; ---------------- σύνθεση κειμένων ----------------
(defun dl:eidosG () (nth (dl:geti "eidos") *DL-EIDOSG*))
(defun dl:P () "\\P")
(defun dl:++ (n) (itoa n))

(defun dl:txt-651 ( / s n loc)
  (setq s "")
  (setq s (strcat
    "\\U+039F \\U+03C5\\U+03C0\\U+03BF\\U+03B3\\U+03C1\\U+03AC\\U+03C6\\U+03C9\\U+03BD " (dl:get "mix")
    (if (dl:nz (dl:get "eid")) (strcat ", " (dl:get "eid")) "")
    (if (dl:nz (dl:get "tee")) (strcat ", \\U+03BC\\U+03B5 \\U+0391.\\U+039C. \\U+03A4.\\U+0395.\\U+0395. " (dl:get "tee")) "")
    ", \\U+03B4\\U+03B7\\U+03BB\\U+03CE\\U+03BD\\U+03C9 \\U+03C5\\U+03C0\\U+03B5\\U+03CD\\U+03B8\\U+03C5\\U+03BD\\U+03B1 \\U+03BA\\U+03B1\\U+03B9 \\U+03B5\\U+03BD \\U+03B3\\U+03BD\\U+03CE\\U+03C3\\U+03B5\\U+03B9 \\U+03C4\\U+03C9\\U+03BD \\U+03C3\\U+03C5\\U+03BD\\U+03B5\\U+03C0\\U+03B5\\U+03B9\\U+03CE\\U+03BD \\U+03C4\\U+03BF\\U+03C5 \\U+03BD\\U+03CC\\U+03BC\\U+03BF\\U+03C5 \\U+03CC\\U+03C4\\U+03B9 \\U+03C4\\U+03BF \\U+03B5\\U+03B9\\U+03BA\\U+03BF\\U+03BD\\U+03B9\\U+03B6\\U+03CC\\U+03BC\\U+03B5\\U+03BD\\U+03BF "
    (dl:eidosG)
    (if (dl:nz (dl:get "kor")) (strcat " \\U+03BC\\U+03B5 \\U+03C3\\U+03C4\\U+03BF\\U+03B9\\U+03C7\\U+03B5\\U+03AF\\U+03B1 " (dl:get "kor")) "")
    (if (dl:nz (dl:get "emb")) (strcat " \\U+03BA\\U+03B1\\U+03B9 \\U+03B5\\U+03BC\\U+03B2\\U+03B1\\U+03B4\\U+03CC\\U+03BD \\U+0395 = " (dl:get "emb") " \\U+03C4.\\U+03BC.") "")
    (if (dl:nz (dl:get "thesi")) (strcat ", \\U+03C3\\U+03C4\\U+03B7 \\U+03B8\\U+03AD\\U+03C3\\U+03B7 " (dl:get "thesi")) "")
    (if (dl:nz (dl:get "dk")) (strcat " \\U+03C4\\U+03B7\\U+03C2 \\U+0394.\\U+039A./\\U+03A4.\\U+039A. " (dl:get "dk")) "")
    (if (dl:nz (dl:get "dimos")) (strcat " \\U+03C4\\U+03BF\\U+03C5 \\U+0394\\U+03AE\\U+03BC\\U+03BF\\U+03C5 " (dl:get "dimos")) "")
    (if (dl:nz (dl:get "pe")) (strcat " \\U+03C4\\U+03B7\\U+03C2 \\U+03A0.\\U+0395. " (dl:get "pe")) "")
    ":"))
  (setq n 1)
  ;; 1. θέση
  (setq loc (cond
    ((= (dl:get "pos") "0") (strcat "\\U+0392\\U+03C1\\U+03AF\\U+03C3\\U+03BA\\U+03B5\\U+03C4\\U+03B1\\U+03B9 \\U+03B5\\U+03BD\\U+03C4\\U+03CC\\U+03C2 \\U+03B5\\U+03B3\\U+03BA\\U+03B5\\U+03BA\\U+03C1\\U+03B9\\U+03BC\\U+03AD\\U+03BD\\U+03BF\\U+03C5 \\U+03C1\\U+03C5\\U+03BC\\U+03BF\\U+03C4\\U+03BF\\U+03BC\\U+03B9\\U+03BA\\U+03BF\\U+03CD \\U+03C3\\U+03C7\\U+03B5\\U+03B4\\U+03AF\\U+03BF\\U+03C5"
        (if (dl:nz (dl:get "ot")) (strcat ", \\U+03C3\\U+03C4\\U+03BF \\U+039F.\\U+03A4. " (dl:get "ot")) "")
        (if (dl:nz (dl:get "fekrym")) (strcat " (\\U+03A6\\U+0395\\U+039A \\U+03C1\\U+03C5\\U+03BC\\U+03BF\\U+03C4\\U+03BF\\U+03BC\\U+03B9\\U+03BA\\U+03BF\\U+03CD: " (dl:get "fekrym") ")") "")))
    ((= (dl:get "pos") "1") "\\U+0392\\U+03C1\\U+03AF\\U+03C3\\U+03BA\\U+03B5\\U+03C4\\U+03B1\\U+03B9 \\U+03B5\\U+03BD\\U+03C4\\U+03CC\\U+03C2 \\U+03C4\\U+03C9\\U+03BD \\U+03BF\\U+03C1\\U+03AF\\U+03C9\\U+03BD \\U+03BF\\U+03B9\\U+03BA\\U+03B9\\U+03C3\\U+03BC\\U+03BF\\U+03CD \\U+03C0\\U+03C1\\U+03BF\\U+03CB\\U+03C6\\U+03B9\\U+03C3\\U+03C4\\U+03B1\\U+03BC\\U+03AD\\U+03BD\\U+03BF\\U+03C5 \\U+03C4\\U+03BF\\U+03C5 \\U+03AD\\U+03C4\\U+03BF\\U+03C5\\U+03C2 1923")
    ((= (dl:get "pos") "2") (strcat "\\U+0392\\U+03C1\\U+03AF\\U+03C3\\U+03BA\\U+03B5\\U+03C4\\U+03B1\\U+03B9 \\U+03B5\\U+03BD\\U+03C4\\U+03CC\\U+03C2 \\U+03C4\\U+03C9\\U+03BD \\U+03BF\\U+03C1\\U+03AF\\U+03C9\\U+03BD \\U+03BF\\U+03B9\\U+03BA\\U+03B9\\U+03C3\\U+03BC\\U+03BF\\U+03CD \\U+03BC\\U+03B5 \\U+03C0\\U+03BB\\U+03B7\\U+03B8\\U+03C5\\U+03C3\\U+03BC\\U+03CC \\U+03BA\\U+03AC\\U+03C4\\U+03C9 \\U+03C4\\U+03C9\\U+03BD 2.000 \\U+03BA\\U+03B1\\U+03C4\\U+03BF\\U+03AF\\U+03BA\\U+03C9\\U+03BD, \\U+03BF\\U+03C1\\U+03B9\\U+03BF\\U+03B8\\U+03B5\\U+03C4\\U+03B7\\U+03BC\\U+03AD\\U+03BD\\U+03BF\\U+03C5 \\U+03BA\\U+03B1\\U+03C4\\U+03AC \\U+03C4\\U+03B9\\U+03C2 \\U+03B4\\U+03B9\\U+03B1\\U+03C4\\U+03AC\\U+03BE\\U+03B5\\U+03B9\\U+03C2 \\U+03C4\\U+03BF\\U+03C5 \\U+03B1\\U+03C0\\U+03CC 24.4.1985 \\U+03A0.\\U+0394."
        (if (dl:nz (dl:get "oikfek")) (strcat " (\\U+03A6\\U+0395\\U+039A \\U+03BF\\U+03C1\\U+03AF\\U+03C9\\U+03BD: " (dl:get "oikfek") ")") "")))
    (T "\\U+0392\\U+03C1\\U+03AF\\U+03C3\\U+03BA\\U+03B5\\U+03C4\\U+03B1\\U+03B9 \\U+03B5\\U+03BA\\U+03C4\\U+03CC\\U+03C2 \\U+03B5\\U+03B3\\U+03BA\\U+03B5\\U+03BA\\U+03C1\\U+03B9\\U+03BC\\U+03AD\\U+03BD\\U+03BF\\U+03C5 \\U+03C1\\U+03C5\\U+03BC\\U+03BF\\U+03C4\\U+03BF\\U+03BC\\U+03B9\\U+03BA\\U+03BF\\U+03CD \\U+03C3\\U+03C7\\U+03B5\\U+03B4\\U+03AF\\U+03BF\\U+03C5 \\U+03BA\\U+03B1\\U+03B9 \\U+03B5\\U+03BA\\U+03C4\\U+03CC\\U+03C2 \\U+03BF\\U+03C1\\U+03AF\\U+03C9\\U+03BD \\U+03BF\\U+03B9\\U+03BA\\U+03B9\\U+03C3\\U+03BC\\U+03BF\\U+03CD")))
  (setq s (strcat s (dl:P) (dl:++ n) ". " loc "."))
  (setq n (1+ n))
  ;; 2. θεσμικό πλαίσιο
  (if (= (dl:get "gps") "1")
    (progn (setq s (strcat s (dl:P) (dl:++ n) ". "
      "\\U+0395\\U+03BC\\U+03C0\\U+03AF\\U+03C0\\U+03C4\\U+03B5\\U+03B9 \\U+03C3\\U+03B5 \\U+03C0\\U+03B5\\U+03C1\\U+03B9\\U+03BF\\U+03C7\\U+03AE \\U+03B5\\U+03B3\\U+03BA\\U+03B5\\U+03BA\\U+03C1\\U+03B9\\U+03BC\\U+03AD\\U+03BD\\U+03BF\\U+03C5 \\U+0393.\\U+03A0.\\U+03A3. / \\U+03A3.\\U+03A7.\\U+039F.\\U+039F.\\U+0391.\\U+03A0. / \\U+03A4.\\U+03A0.\\U+03A3."
      (if (dl:nz (dl:get "gpsfek")) (strcat " (" (dl:get "gpsfek") ")") "") "."))
           (setq n (1+ n))))
  (if (= (dl:get "zoe") "1")
    (progn (setq s (strcat s (dl:P) (dl:++ n) ". "
      "\\U+0395\\U+03BC\\U+03C0\\U+03AF\\U+03C0\\U+03C4\\U+03B5\\U+03B9 \\U+03C3\\U+03B5 \\U+0396\\U+03CE\\U+03BD\\U+03B7 \\U+039F\\U+03B9\\U+03BA\\U+03B9\\U+03C3\\U+03C4\\U+03B9\\U+03BA\\U+03BF\\U+03CD \\U+0395\\U+03BB\\U+03AD\\U+03B3\\U+03C7\\U+03BF\\U+03C5 / \\U+03B6\\U+03CE\\U+03BD\\U+03B7 \\U+03B5\\U+03B9\\U+03B4\\U+03B9\\U+03BA\\U+03CE\\U+03BD \\U+03C7\\U+03C1\\U+03AE\\U+03C3\\U+03B5\\U+03C9\\U+03BD \\U+03BA\\U+03B1\\U+03B9 \\U+03CC\\U+03C1\\U+03C9\\U+03BD \\U+03B4\\U+03CC\\U+03BC\\U+03B7\\U+03C3\\U+03B7\\U+03C2"
      (if (dl:nz (dl:get "zoefek")) (strcat " (" (dl:get "zoefek") ")") "") "."))
           (setq n (1+ n))))
  (if (= (dl:get "parad") "1")
    (progn (setq s (strcat s (dl:P) (dl:++ n) ". "
      "\\U+0395\\U+03BC\\U+03C0\\U+03AF\\U+03C0\\U+03C4\\U+03B5\\U+03B9 \\U+03C3\\U+03B5 \\U+03C7\\U+03B1\\U+03C1\\U+03B1\\U+03BA\\U+03C4\\U+03B7\\U+03C1\\U+03B9\\U+03C3\\U+03BC\\U+03AD\\U+03BD\\U+03BF \\U+03C0\\U+03B1\\U+03C1\\U+03B1\\U+03B4\\U+03BF\\U+03C3\\U+03B9\\U+03B1\\U+03BA\\U+03CC \\U+03BF\\U+03B9\\U+03BA\\U+03B9\\U+03C3\\U+03BC\\U+03CC / \\U+03B9\\U+03C3\\U+03C4\\U+03BF\\U+03C1\\U+03B9\\U+03BA\\U+03CC \\U+03C4\\U+03CC\\U+03C0\\U+03BF \\U+03BA\\U+03B1\\U+03B9 \\U+03B9\\U+03C3\\U+03C7\\U+03CD\\U+03BF\\U+03C5\\U+03BD \\U+03BF\\U+03B9 \\U+03B5\\U+03B9\\U+03B4\\U+03B9\\U+03BA\\U+03BF\\U+03AF \\U+03CC\\U+03C1\\U+03BF\\U+03B9 \\U+03BA\\U+03B1\\U+03B9 \\U+03C0\\U+03B5\\U+03C1\\U+03B9\\U+03BF\\U+03C1\\U+03B9\\U+03C3\\U+03BC\\U+03BF\\U+03AF \\U+03B4\\U+03CC\\U+03BC\\U+03B7\\U+03C3\\U+03B7\\U+03C2 \\U+03B1\\U+03C5\\U+03C4\\U+03BF\\U+03CD."))
           (setq n (1+ n))))
  ;; 3. αρτιότητα
  (setq s (strcat s (dl:P) (dl:++ n) ". "
    (if (= (dl:get "artio") "1")
      (strcat "\\U+0395\\U+03AF\\U+03BD\\U+03B1\\U+03B9 \\U+03AC\\U+03C1\\U+03C4\\U+03B9\\U+03BF " (nth (dl:geti "vasi") *DL-VASI*)
        (if (dl:nz (dl:get "artemb")) (strcat " (\\U+03B5\\U+03BB\\U+03AC\\U+03C7\\U+03B9\\U+03C3\\U+03C4\\U+03BF \\U+03B5\\U+03BC\\U+03B2\\U+03B1\\U+03B4\\U+03CC\\U+03BD \\U+03B1\\U+03C1\\U+03C4\\U+03B9\\U+03CC\\U+03C4\\U+03B7\\U+03C4\\U+03B1\\U+03C2 " (dl:get "artemb") " \\U+03C4.\\U+03BC.)") "")
        (if (= (dl:get "oik") "1") " \\U+03BA\\U+03B1\\U+03B9 \\U+03BF\\U+03B9\\U+03BA\\U+03BF\\U+03B4\\U+03BF\\U+03BC\\U+03AE\\U+03C3\\U+03B9\\U+03BC\\U+03BF" ", \\U+03C0\\U+03BB\\U+03B7\\U+03BD \\U+03CC\\U+03BC\\U+03C9\\U+03C2 \\U+03BC\\U+03B7 \\U+03BF\\U+03B9\\U+03BA\\U+03BF\\U+03B4\\U+03BF\\U+03BC\\U+03AE\\U+03C3\\U+03B9\\U+03BC\\U+03BF")
        ", \\U+03C3\\U+03CD\\U+03BC\\U+03C6\\U+03C9\\U+03BD\\U+03B1 \\U+03BC\\U+03B5 \\U+03C4\\U+03B9\\U+03C2 \\U+03B9\\U+03C3\\U+03C7\\U+03CD\\U+03BF\\U+03C5\\U+03C3\\U+03B5\\U+03C2 \\U+03C0\\U+03BF\\U+03BB\\U+03B5\\U+03BF\\U+03B4\\U+03BF\\U+03BC\\U+03B9\\U+03BA\\U+03AD\\U+03C2 \\U+03B4\\U+03B9\\U+03B1\\U+03C4\\U+03AC\\U+03BE\\U+03B5\\U+03B9\\U+03C2")
      (strcat "\\U+0394\\U+03B5\\U+03BD \\U+03B5\\U+03AF\\U+03BD\\U+03B1\\U+03B9 \\U+03AC\\U+03C1\\U+03C4\\U+03B9\\U+03BF \\U+03BA\\U+03B1\\U+03B9 \\U+03B4\\U+03B5\\U+03BD \\U+03B5\\U+03AF\\U+03BD\\U+03B1\\U+03B9 \\U+03BF\\U+03B9\\U+03BA\\U+03BF\\U+03B4\\U+03BF\\U+03BC\\U+03AE\\U+03C3\\U+03B9\\U+03BC\\U+03BF \\U+03C3\\U+03CD\\U+03BC\\U+03C6\\U+03C9\\U+03BD\\U+03B1 \\U+03BC\\U+03B5 \\U+03C4\\U+03B9\\U+03C2 \\U+03B9\\U+03C3\\U+03C7\\U+03CD\\U+03BF\\U+03C5\\U+03C3\\U+03B5\\U+03C2 \\U+03C0\\U+03BF\\U+03BB\\U+03B5\\U+03BF\\U+03B4\\U+03BF\\U+03BC\\U+03B9\\U+03BA\\U+03AD\\U+03C2 \\U+03B4\\U+03B9\\U+03B1\\U+03C4\\U+03AC\\U+03BE\\U+03B5\\U+03B9\\U+03C2"))
    "."))
  (setq n (1+ n))
  ;; 4. πρόσωπο
  (if (dl:nz (dl:get "pros"))
    (progn (setq s (strcat s (dl:P) (dl:++ n) ". "
      "\\U+0388\\U+03C7\\U+03B5\\U+03B9 \\U+03C0\\U+03C1\\U+03CC\\U+03C3\\U+03C9\\U+03C0\\U+03BF " (dl:get "pros") " \\U+03BC. \\U+03C3\\U+03B5 " (nth (dl:geti "odos") *DL-ODOS*) "."))
           (setq n (1+ n))))
  ;; 5. κατάτμηση
  (if (= (dl:get "katat") "1")
    (progn (setq s (strcat s (dl:P) (dl:++ n) ". "
      "\\U+0394\\U+03B5\\U+03BD \\U+03C0\\U+03C1\\U+03BF\\U+03AE\\U+03BB\\U+03B8\\U+03B5 \\U+03B1\\U+03C0\\U+03CC \\U+03BA\\U+03B1\\U+03C4\\U+03AC\\U+03C4\\U+03BC\\U+03B7\\U+03C3\\U+03B7"
      (if (dl:nz (dl:get "katdate")) (strcat " \\U+03BC\\U+03B5\\U+03C4\\U+03AC \\U+03C4\\U+03B7\\U+03BD " (dl:get "katdate")) "") "."))
           (setq n (1+ n))))
  ;; 6. Ν.1337/83
  (setq s (strcat s (dl:P) (dl:++ n) ". "
    (if (= (dl:get "n1337") "1")
      (strcat "\\U+03A5\\U+03C0\\U+03AC\\U+03B3\\U+03B5\\U+03C4\\U+03B1\\U+03B9 \\U+03C3\\U+03C4\\U+03B9\\U+03C2 \\U+03B4\\U+03B9\\U+03B1\\U+03C4\\U+03AC\\U+03BE\\U+03B5\\U+03B9\\U+03C2 \\U+03C4\\U+03BF\\U+03C5 \\U+039D.1337/83 \\U+03BA\\U+03B1\\U+03B9 "
        (cond
          ((and (= (dl:get "eisgi") "1") (= (dl:get "eisxr") "1")) "\\U+03BF\\U+03C6\\U+03B5\\U+03AF\\U+03BB\\U+03B5\\U+03B9 \\U+03B5\\U+03B9\\U+03C3\\U+03C6\\U+03BF\\U+03C1\\U+03AC \\U+03C3\\U+03B5 \\U+03B3\\U+03B7 \\U+03BA\\U+03B1\\U+03B9 \\U+03C3\\U+03B5 \\U+03C7\\U+03C1\\U+03AE\\U+03BC\\U+03B1")
          ((= (dl:get "eisgi") "1") "\\U+03BF\\U+03C6\\U+03B5\\U+03AF\\U+03BB\\U+03B5\\U+03B9 \\U+03B5\\U+03B9\\U+03C3\\U+03C6\\U+03BF\\U+03C1\\U+03AC \\U+03C3\\U+03B5 \\U+03B3\\U+03B7")
          ((= (dl:get "eisxr") "1") "\\U+03BF\\U+03C6\\U+03B5\\U+03AF\\U+03BB\\U+03B5\\U+03B9 \\U+03B5\\U+03B9\\U+03C3\\U+03C6\\U+03BF\\U+03C1\\U+03AC \\U+03C3\\U+03B5 \\U+03C7\\U+03C1\\U+03AE\\U+03BC\\U+03B1")
          (T "\\U+03B4\\U+03B5\\U+03BD \\U+03BF\\U+03C6\\U+03B5\\U+03AF\\U+03BB\\U+03B5\\U+03B9 \\U+03B5\\U+03B9\\U+03C3\\U+03C6\\U+03BF\\U+03C1\\U+03AC \\U+03C3\\U+03B5 \\U+03B3\\U+03B7 \\U+03BA\\U+03B1\\U+03B9 \\U+03C3\\U+03B5 \\U+03C7\\U+03C1\\U+03AE\\U+03BC\\U+03B1"))
        ". \\U+0397 \\U+03C0\\U+03C1\\U+03AC\\U+03BE\\U+03B7 \\U+03B5\\U+03C6\\U+03B1\\U+03C1\\U+03BC\\U+03BF\\U+03B3\\U+03AE\\U+03C2 \\U+03B5\\U+03AF\\U+03BD\\U+03B1\\U+03B9 " (nth (dl:geti "praxi") *DL-PRAXI*))
      "\\U+0394\\U+03B5\\U+03BD \\U+03C5\\U+03C0\\U+03AC\\U+03B3\\U+03B5\\U+03C4\\U+03B1\\U+03B9 \\U+03C3\\U+03C4\\U+03B9\\U+03C2 \\U+03B4\\U+03B9\\U+03B1\\U+03C4\\U+03AC\\U+03BE\\U+03B5\\U+03B9\\U+03C2 \\U+03C4\\U+03BF\\U+03C5 \\U+039D.1337/83 \\U+03BA\\U+03B1\\U+03B9 \\U+03B4\\U+03B5\\U+03BD \\U+03BF\\U+03C6\\U+03B5\\U+03AF\\U+03BB\\U+03B5\\U+03B9 \\U+03B5\\U+03B9\\U+03C3\\U+03C6\\U+03BF\\U+03C1\\U+03AC \\U+03C3\\U+03B5 \\U+03B3\\U+03B7 \\U+03BA\\U+03B1\\U+03B9 \\U+03C3\\U+03B5 \\U+03C7\\U+03C1\\U+03AE\\U+03BC\\U+03B1")
    "."))
  (setq n (1+ n))
  ;; 7. Ν.2242/94
  (setq s (strcat s (dl:P) (dl:++ n) ". "
    (if (= (dl:get "n2242") "1")
      "\\U+0395\\U+03BC\\U+03C0\\U+03AF\\U+03C0\\U+03C4\\U+03B5\\U+03B9 \\U+03C3\\U+03C4\\U+03B9\\U+03C2 \\U+03B4\\U+03B9\\U+03B1\\U+03C4\\U+03AC\\U+03BE\\U+03B5\\U+03B9\\U+03C2 \\U+03C4\\U+03BF\\U+03C5 \\U+039D.2242/94 (\\U+03C0\\U+03B5\\U+03C1\\U+03AF \\U+03B4\\U+03B7\\U+03BB\\U+03CE\\U+03C3\\U+03B5\\U+03C9\\U+03C2 \\U+03B9\\U+03B4\\U+03B9\\U+03BF\\U+03BA\\U+03C4\\U+03B7\\U+03C3\\U+03AF\\U+03B1\\U+03C2 \\U+03C3\\U+03C4\\U+03BF\\U+03BD \\U+039F.\\U+03A4.\\U+0391.)"
      "\\U+0394\\U+03B5\\U+03BD \\U+03B5\\U+03BC\\U+03C0\\U+03AF\\U+03C0\\U+03C4\\U+03B5\\U+03B9 \\U+03C3\\U+03C4\\U+03B9\\U+03C2 \\U+03B4\\U+03B9\\U+03B1\\U+03C4\\U+03AC\\U+03BE\\U+03B5\\U+03B9\\U+03C2 \\U+03C4\\U+03BF\\U+03C5 \\U+039D.2242/94") "."))
  (setq n (1+ n))
  ;; 8. κτηματολόγιο
  (setq s (strcat s (dl:P) (dl:++ n) ". "
    (if (= (dl:get "ktim") "1")
      (strcat "\\U+0395\\U+03BC\\U+03C0\\U+03AF\\U+03C0\\U+03C4\\U+03B5\\U+03B9 \\U+03C3\\U+03B5 \\U+03C0\\U+03B5\\U+03C1\\U+03B9\\U+03BF\\U+03C7\\U+03AE \\U+03BB\\U+03B5\\U+03B9\\U+03C4\\U+03BF\\U+03C5\\U+03C1\\U+03B3\\U+03AF\\U+03B1\\U+03C2 \\U+0395\\U+03B8\\U+03BD\\U+03B9\\U+03BA\\U+03BF\\U+03CD \\U+039A\\U+03C4\\U+03B7\\U+03BC\\U+03B1\\U+03C4\\U+03BF\\U+03BB\\U+03BF\\U+03B3\\U+03AF\\U+03BF\\U+03C5 (\\U+039D.2308/95)"
        (if (dl:nz (dl:get "kaek")) (strcat " \\U+03BC\\U+03B5 \\U+039A\\U+0391\\U+0395\\U+039A " (dl:get "kaek")) ""))
      "\\U+0394\\U+03B5\\U+03BD \\U+03B5\\U+03BC\\U+03C0\\U+03AF\\U+03C0\\U+03C4\\U+03B5\\U+03B9 \\U+03C3\\U+03B5 \\U+03C0\\U+03B5\\U+03C1\\U+03B9\\U+03BF\\U+03C7\\U+03AE \\U+03BB\\U+03B5\\U+03B9\\U+03C4\\U+03BF\\U+03C5\\U+03C1\\U+03B3\\U+03AF\\U+03B1\\U+03C2 \\U+0395\\U+03B8\\U+03BD\\U+03B9\\U+03BA\\U+03BF\\U+03CD \\U+039A\\U+03C4\\U+03B7\\U+03BC\\U+03B1\\U+03C4\\U+03BF\\U+03BB\\U+03BF\\U+03B3\\U+03AF\\U+03BF\\U+03C5") "."))
  (setq n (1+ n))
  ;; 9. δεσμεύσεις
  (setq s (strcat s (dl:P) (dl:++ n) ". " (dl:txt-desm) "."))
  (setq n (1+ n))
  ;; κλείσιμο
  (setq s (strcat s (dl:P) (dl:++ n) ". "
    "\\U+03A4\\U+03BF \\U+03C0\\U+03B1\\U+03C1\\U+03CC\\U+03BD \\U+03C4\\U+03BF\\U+03C0\\U+03BF\\U+03B3\\U+03C1\\U+03B1\\U+03C6\\U+03B9\\U+03BA\\U+03CC \\U+03B4\\U+03B9\\U+03AC\\U+03B3\\U+03C1\\U+03B1\\U+03BC\\U+03BC\\U+03B1 \\U+03C3\\U+03C5\\U+03BD\\U+03C4\\U+03AC\\U+03C7\\U+03B8\\U+03B7\\U+03BA\\U+03B5 \\U+03BC\\U+03B5 \\U+03B5\\U+03BE\\U+03AC\\U+03C1\\U+03C4\\U+03B7\\U+03C3\\U+03B7 \\U+03B1\\U+03C0\\U+03CC \\U+03C4\\U+03BF \\U+039A\\U+03C1\\U+03B1\\U+03C4\\U+03B9\\U+03BA\\U+03CC \\U+03A3\\U+03CD\\U+03C3\\U+03C4\\U+03B7\\U+03BC\\U+03B1 \\U+03A3\\U+03C5\\U+03BD\\U+03C4\\U+03B5\\U+03C4\\U+03B1\\U+03B3\\U+03BC\\U+03AD\\U+03BD\\U+03C9\\U+03BD \\U+0395.\\U+0393.\\U+03A3.\\U+0391. 1987 \\U+03BA\\U+03B1\\U+03B9 \\U+03BF\\U+03B9 \\U+03B1\\U+03BD\\U+03B1\\U+03B3\\U+03C1\\U+03B1\\U+03C6\\U+03CC\\U+03BC\\U+03B5\\U+03BD\\U+03B5\\U+03C2 \\U+03C3\\U+03C5\\U+03BD\\U+03C4\\U+03B5\\U+03C4\\U+03B1\\U+03B3\\U+03BC\\U+03AD\\U+03BD\\U+03B5\\U+03C2 \\U+03C4\\U+03C9\\U+03BD \\U+03BA\\U+03BF\\U+03C1\\U+03C5\\U+03C6\\U+03CE\\U+03BD \\U+03C0\\U+03C1\\U+03BF\\U+03BA\\U+03CD\\U+03C0\\U+03C4\\U+03BF\\U+03C5\\U+03BD \\U+03B1\\U+03C0\\U+03CC \\U+03B1\\U+03C5\\U+03C4\\U+03CC."))
  s)

(defun dl:txt-desm ( / a b)
  (setq a nil)
  (if (= (dl:get "aig") "1")
    (setq a (cons "\\U+03B5\\U+03BD\\U+03C4\\U+03CC\\U+03C2 \\U+03BA\\U+03B1\\U+03B8\\U+03BF\\U+03C1\\U+03B9\\U+03C3\\U+03BC\\U+03AD\\U+03BD\\U+03B7\\U+03C2 \\U+03B6\\U+03CE\\U+03BD\\U+03B7\\U+03C2 \\U+03B1\\U+03B9\\U+03B3\\U+03B9\\U+03B1\\U+03BB\\U+03BF\\U+03CD/\\U+03C0\\U+03B1\\U+03C1\\U+03B1\\U+03BB\\U+03AF\\U+03B1\\U+03C2" a))
    (if (dl:nz (dl:get "aigd"))
      (setq a (cons (strcat "\\U+03B5\\U+03BA\\U+03C4\\U+03CC\\U+03C2 \\U+03B6\\U+03CE\\U+03BD\\U+03B7\\U+03C2 \\U+03B1\\U+03B9\\U+03B3\\U+03B9\\U+03B1\\U+03BB\\U+03BF\\U+03CD/\\U+03C0\\U+03B1\\U+03C1\\U+03B1\\U+03BB\\U+03AF\\U+03B1\\U+03C2, \\U+03C3\\U+03B5 \\U+03B1\\U+03C0\\U+03CC\\U+03C3\\U+03C4\\U+03B1\\U+03C3\\U+03B7 " (dl:get "aigd") " \\U+03BC. \\U+03B1\\U+03C0\\U+03CC \\U+03C4\\U+03B7\\U+03BD \\U+03B1\\U+03BA\\U+03C4\\U+03BF\\U+03B3\\U+03C1\\U+03B1\\U+03BC\\U+03BC\\U+03AE") a))))
  (if (= (dl:get "rema") "1")
    (setq a (cons (strcat "\\U+03C3\\U+03B5 \\U+03B3\\U+03B5\\U+03B9\\U+03C4\\U+03BD\\U+03AF\\U+03B1\\U+03C3\\U+03B7 \\U+03BC\\U+03B5 \\U+03C1\\U+03AD\\U+03BC\\U+03B1"
      (if (dl:nz (dl:get "remad")) (strcat " \\U+03C3\\U+03B5 \\U+03B1\\U+03C0\\U+03CC\\U+03C3\\U+03C4\\U+03B1\\U+03C3\\U+03B7 " (dl:get "remad") " \\U+03BC.") "")) a)))
  (if (= (dl:get "dasos") "1") (setq a (cons "\\U+03B5\\U+03BD\\U+03C4\\U+03CC\\U+03C2 \\U+03AD\\U+03BA\\U+03C4\\U+03B1\\U+03C3\\U+03B7\\U+03C2 \\U+03C7\\U+03B1\\U+03C1\\U+03B1\\U+03BA\\U+03C4\\U+03B7\\U+03C1\\U+03B9\\U+03C3\\U+03BC\\U+03AD\\U+03BD\\U+03B7\\U+03C2 \\U+03C9\\U+03C2 \\U+03B4\\U+03B1\\U+03C3\\U+03B9\\U+03BA\\U+03AE\\U+03C2" a)))
  (if (= (dl:get "arxaio") "1") (setq a (cons "\\U+03B5\\U+03BD\\U+03C4\\U+03CC\\U+03C2 \\U+03B6\\U+03CE\\U+03BD\\U+03B7\\U+03C2 \\U+03B1\\U+03C1\\U+03C7\\U+03B1\\U+03B9\\U+03BF\\U+03BB\\U+03BF\\U+03B3\\U+03B9\\U+03BA\\U+03BF\\U+03CD \\U+03B5\\U+03BD\\U+03B4\\U+03B9\\U+03B1\\U+03C6\\U+03AD\\U+03C1\\U+03BF\\U+03BD\\U+03C4\\U+03BF\\U+03C2" a)))
  (if (= (dl:get "dei") "1") (setq a (cons "\\U+03BC\\U+03B5 \\U+03B4\\U+03B9\\U+03B5\\U+03C1\\U+03C7\\U+03CC\\U+03BC\\U+03B5\\U+03BD\\U+03B7 \\U+03B5\\U+03BD\\U+03B1\\U+03AD\\U+03C1\\U+03B9\\U+03B1 \\U+03B3\\U+03C1\\U+03B1\\U+03BC\\U+03BC\\U+03AE \\U+03C5\\U+03C8\\U+03B7\\U+03BB\\U+03AE\\U+03C2 \\U+03C4\\U+03AC\\U+03C3\\U+03B7\\U+03C2 \\U+03C4\\U+03B7\\U+03C2 \\U+0394.\\U+0395.\\U+0397." a)))
  (if (= (dl:get "aerio") "1") (setq a (cons "\\U+03BC\\U+03B5 \\U+03B4\\U+03B9\\U+03B5\\U+03C1\\U+03C7\\U+03CC\\U+03BC\\U+03B5\\U+03BD\\U+03BF \\U+03B1\\U+03B3\\U+03C9\\U+03B3\\U+03CC \\U+03C6\\U+03C5\\U+03C3\\U+03B9\\U+03BA\\U+03BF\\U+03CD \\U+03B1\\U+03B5\\U+03C1\\U+03AF\\U+03BF\\U+03C5" a)))
  (if (null a)
    "\\U+0394\\U+03B5\\U+03BD \\U+03B5\\U+03BC\\U+03C0\\U+03AF\\U+03C0\\U+03C4\\U+03B5\\U+03B9 \\U+03C3\\U+03B5 \\U+03B6\\U+03CE\\U+03BD\\U+03B7 \\U+03B1\\U+03B9\\U+03B3\\U+03B9\\U+03B1\\U+03BB\\U+03BF\\U+03CD - \\U+03C0\\U+03B1\\U+03C1\\U+03B1\\U+03BB\\U+03AF\\U+03B1\\U+03C2, \\U+03B4\\U+03B5\\U+03BD \\U+03B3\\U+03B5\\U+03B9\\U+03C4\\U+03BD\\U+03B9\\U+03AC\\U+03B6\\U+03B5\\U+03B9 \\U+03BC\\U+03B5 \\U+03C1\\U+03AD\\U+03BC\\U+03B1, \\U+03B4\\U+03B5\\U+03BD \\U+03B5\\U+03BC\\U+03C0\\U+03AF\\U+03C0\\U+03C4\\U+03B5\\U+03B9 \\U+03C3\\U+03B5 \\U+03B4\\U+03B1\\U+03C3\\U+03B9\\U+03BA\\U+03AE \\U+03AE \\U+03B1\\U+03C1\\U+03C7\\U+03B1\\U+03B9\\U+03BF\\U+03BB\\U+03BF\\U+03B3\\U+03B9\\U+03BA\\U+03AE \\U+03B6\\U+03CE\\U+03BD\\U+03B7 \\U+03BA\\U+03B1\\U+03B9 \\U+03B4\\U+03B5\\U+03BD \\U+03B4\\U+03B9\\U+03AD\\U+03C1\\U+03C7\\U+03BF\\U+03BD\\U+03C4\\U+03B1\\U+03B9 \\U+03B1\\U+03C0\\U+03CC \\U+03B1\\U+03C5\\U+03C4\\U+03CC \\U+03B5\\U+03BD\\U+03B1\\U+03AD\\U+03C1\\U+03B9\\U+03B5\\U+03C2 \\U+03B3\\U+03C1\\U+03B1\\U+03BC\\U+03BC\\U+03AD\\U+03C2 \\U+0394.\\U+0395.\\U+0397. \\U+03AE \\U+03B1\\U+03B3\\U+03C9\\U+03B3\\U+03BF\\U+03AF \\U+03C6\\U+03C5\\U+03C3\\U+03B9\\U+03BA\\U+03BF\\U+03CD \\U+03B1\\U+03B5\\U+03C1\\U+03AF\\U+03BF\\U+03C5"
    (progn
      (setq b "\\U+0392\\U+03C1\\U+03AF\\U+03C3\\U+03BA\\U+03B5\\U+03C4\\U+03B1\\U+03B9 ")
      (setq a (reverse a))
      (setq b (strcat b (car a)))
      (foreach x (cdr a) (setq b (strcat b ", " x)))
      b)))

(defun dl:txt-4030 ( / s)
  (setq s (strcat
    "\\U+039F/\\U+0397 \\U+03C5\\U+03C0\\U+03BF\\U+03B3\\U+03C1\\U+03AC\\U+03C6\\U+03C9\\U+03BD/\\U+03BF\\U+03CD\\U+03C3\\U+03B1 " (dl:get "idio")
    (if (dl:nz (dl:get "pat")) (strcat " \\U+03C4\\U+03BF\\U+03C5 " (dl:get "pat")) "")
    (if (dl:nz (dl:get "afm")) (strcat ", \\U+03BC\\U+03B5 \\U+0391.\\U+03A6.\\U+039C. " (dl:get "afm")) "")
    ", \\U+03B4\\U+03B7\\U+03BB\\U+03CE\\U+03BD\\U+03C9 \\U+03C5\\U+03C0\\U+03B5\\U+03CD\\U+03B8\\U+03C5\\U+03BD\\U+03B1, \\U+03BA\\U+03B1\\U+03C4\\U+03AC \\U+03C4\\U+03B9\\U+03C2 \\U+03B4\\U+03B9\\U+03B1\\U+03C4\\U+03AC\\U+03BE\\U+03B5\\U+03B9\\U+03C2 \\U+03C4\\U+03BF\\U+03C5 \\U+03AC\\U+03C1\\U+03B8\\U+03C1\\U+03BF\\U+03C5 25 \\U+03C4\\U+03BF\\U+03C5 \\U+039D.4030/2011 \\U+03BA\\U+03B1\\U+03B9 \\U+03C4\\U+03BF\\U+03C5 \\U+039D.1599/1986, \\U+03B5\\U+03BD \\U+03B3\\U+03BD\\U+03CE\\U+03C3\\U+03B5\\U+03B9 \\U+03C4\\U+03C9\\U+03BD \\U+03C3\\U+03C5\\U+03BD\\U+03B5\\U+03C0\\U+03B5\\U+03B9\\U+03CE\\U+03BD \\U+03C4\\U+03BF\\U+03C5 \\U+03BD\\U+03CC\\U+03BC\\U+03BF\\U+03C5 \\U+03C0\\U+03B5\\U+03C1\\U+03AF \\U+03C8\\U+03B5\\U+03C5\\U+03B4\\U+03BF\\U+03CD\\U+03C2 \\U+03B4\\U+03B7\\U+03BB\\U+03CE\\U+03C3\\U+03B5\\U+03C9\\U+03C2, \\U+03CC\\U+03C4\\U+03B9:"))
  (setq s (strcat s (dl:P) "1. "
    "\\U+03A5\\U+03C0\\U+03AD\\U+03B4\\U+03B5\\U+03B9\\U+03BE\\U+03B1 \\U+03BF \\U+03AF\\U+03B4\\U+03B9\\U+03BF\\U+03C2 \\U+03B5\\U+03C0\\U+03AF \\U+03C4\\U+03CC\\U+03C0\\U+03BF\\U+03C5 \\U+03C3\\U+03C4\\U+03BF\\U+03BD \\U+03C3\\U+03C5\\U+03BD\\U+03C4\\U+03AC\\U+03BA\\U+03C4\\U+03B7 \\U+03BC\\U+03B7\\U+03C7\\U+03B1\\U+03BD\\U+03B9\\U+03BA\\U+03CC \\U+03C4\\U+03B7 \\U+03B8\\U+03AD\\U+03C3\\U+03B7 \\U+03BA\\U+03B1\\U+03B9 \\U+03C4\\U+03B1 \\U+03CC\\U+03C1\\U+03B9\\U+03B1 \\U+03C4\\U+03BF\\U+03C5 "
    (dl:eidosG)
    (if (dl:nz (dl:get "kor")) (strcat ", \\U+03CC\\U+03C0\\U+03C9\\U+03C2 \\U+03B1\\U+03C5\\U+03C4\\U+03AC \\U+03B1\\U+03C0\\U+03BF\\U+03C4\\U+03C5\\U+03C0\\U+03CE\\U+03BD\\U+03BF\\U+03BD\\U+03C4\\U+03B1\\U+03B9 \\U+03C3\\U+03C4\\U+03BF \\U+03C0\\U+03B1\\U+03C1\\U+03CC\\U+03BD \\U+03B4\\U+03B9\\U+03AC\\U+03B3\\U+03C1\\U+03B1\\U+03BC\\U+03BC\\U+03B1 \\U+03BC\\U+03B5 \\U+03C4\\U+03B1 \\U+03C3\\U+03C4\\U+03BF\\U+03B9\\U+03C7\\U+03B5\\U+03AF\\U+03B1 " (dl:get "kor")) "")
    ", \\U+03C4\\U+03B1 \\U+03BF\\U+03C0\\U+03BF\\U+03AF\\U+03B1 \\U+03B5\\U+03AF\\U+03BD\\U+03B1\\U+03B9 \\U+03C4\\U+03B1 \\U+03C0\\U+03C1\\U+03B1\\U+03B3\\U+03BC\\U+03B1\\U+03C4\\U+03B9\\U+03BA\\U+03AC \\U+03CC\\U+03C1\\U+03B9\\U+03B1 \\U+03C4\\U+03B7\\U+03C2 \\U+03B9\\U+03B4\\U+03B9\\U+03BF\\U+03BA\\U+03C4\\U+03B7\\U+03C3\\U+03AF\\U+03B1\\U+03C2 \\U+03BC\\U+03BF\\U+03C5 \\U+03BA\\U+03B1\\U+03B9 \\U+03B4\\U+03B5\\U+03BD \\U+03BA\\U+03B1\\U+03C4\\U+03B1\\U+03C0\\U+03B1\\U+03C4\\U+03BF\\U+03CD\\U+03BD \\U+03CC\\U+03BC\\U+03BF\\U+03C1\\U+03B5\\U+03C2 \\U+03B9\\U+03B4\\U+03B9\\U+03BF\\U+03BA\\U+03C4\\U+03B7\\U+03C3\\U+03AF\\U+03B5\\U+03C2 \\U+03AE \\U+03BA\\U+03BF\\U+03B9\\U+03BD\\U+03CC\\U+03C7\\U+03C1\\U+03B7\\U+03C3\\U+03C4\\U+03BF\\U+03C5\\U+03C2 \\U+03C7\\U+03CE\\U+03C1\\U+03BF\\U+03C5\\U+03C2."))
  (setq s (strcat s (dl:P) "2. "
    "\\U+0388\\U+03C7\\U+03C9 \\U+03C4\\U+03BF \\U+03BD\\U+03CC\\U+03BC\\U+03B9\\U+03BC\\U+03BF \\U+03B4\\U+03B9\\U+03BA\\U+03B1\\U+03AF\\U+03C9\\U+03BC\\U+03B1 \\U+03BD\\U+03B1 \\U+03B1\\U+03BD\\U+03B1\\U+03B8\\U+03AD\\U+03C3\\U+03C9 \\U+03C4\\U+03B7 \\U+03C3\\U+03CD\\U+03BD\\U+03C4\\U+03B1\\U+03BE\\U+03B7 \\U+03C4\\U+03BF\\U+03C5 \\U+03C0\\U+03B1\\U+03C1\\U+03CC\\U+03BD\\U+03C4\\U+03BF\\U+03C2 \\U+03C4\\U+03BF\\U+03C0\\U+03BF\\U+03B3\\U+03C1\\U+03B1\\U+03C6\\U+03B9\\U+03BA\\U+03BF\\U+03CD \\U+03B4\\U+03B9\\U+03B1\\U+03B3\\U+03C1\\U+03AC\\U+03BC\\U+03BC\\U+03B1\\U+03C4\\U+03BF\\U+03C2 \\U+03C3\\U+03C4\\U+03BF\\U+03BD \\U+03C9\\U+03C2 \\U+03AC\\U+03BD\\U+03C9 \\U+03BC\\U+03B7\\U+03C7\\U+03B1\\U+03BD\\U+03B9\\U+03BA\\U+03CC."))
  (setq s (strcat s (dl:P) "3. "
    "\\U+03A4\\U+03B1 \\U+03C3\\U+03C4\\U+03BF\\U+03B9\\U+03C7\\U+03B5\\U+03AF\\U+03B1 \\U+03BA\\U+03B1\\U+03B9 \\U+03BF\\U+03B9 \\U+03C0\\U+03BB\\U+03B7\\U+03C1\\U+03BF\\U+03C6\\U+03BF\\U+03C1\\U+03AF\\U+03B5\\U+03C2 \\U+03C0\\U+03BF\\U+03C5 \\U+03B4\\U+03AE\\U+03BB\\U+03C9\\U+03C3\\U+03B1 \\U+03BA\\U+03B1\\U+03B9 \\U+03C0\\U+03B1\\U+03C1\\U+03AD\\U+03B4\\U+03C9\\U+03C3\\U+03B1 \\U+03C3\\U+03C4\\U+03BF\\U+03BD \\U+03BC\\U+03B7\\U+03C7\\U+03B1\\U+03BD\\U+03B9\\U+03BA\\U+03CC \\U+03B3\\U+03B9\\U+03B1 \\U+03C4\\U+03B7 \\U+03C3\\U+03CD\\U+03BD\\U+03C4\\U+03B1\\U+03BE\\U+03B7 \\U+03C4\\U+03BF\\U+03C5 \\U+03C0\\U+03B1\\U+03C1\\U+03CC\\U+03BD\\U+03C4\\U+03BF\\U+03C2 \\U+03B5\\U+03AF\\U+03BD\\U+03B1\\U+03B9 \\U+03B1\\U+03BB\\U+03B7\\U+03B8\\U+03AE \\U+03BA\\U+03B1\\U+03B9 \\U+03B1\\U+03BA\\U+03C1\\U+03B9\\U+03B2\\U+03AE."))
  s)

;; ---------------- έξοδος στο σχέδιο ----------------
(defun dl:style ( / )
  (if (not (tblsearch "STYLE" "BRB_GR"))
    (entmake (list (cons 0 "STYLE") (cons 100 "AcDbSymbolTableRecord")
                   (cons 100 "AcDbTextStyleTableRecord") (cons 2 "BRB_GR")
                   (cons 70 0) (cons 40 0.0) (cons 41 0.9) (cons 50 0.0)
                   (cons 71 0) (cons 42 2.5) (cons 3 "arial.ttf") (cons 4 ""))))
  "BRB_GR")

(defun dl:layer (nm col)
  (if (not (tblsearch "LAYER" nm))
    (entmake (list (cons 0 "LAYER") (cons 100 "AcDbSymbolTableRecord")
                   (cons 100 "AcDbLayerTableRecord") (cons 2 nm) (cons 70 0)
                   (cons 62 col) (cons 6 "Continuous"))))
  nm)

(defun dl:sc ( / k)
  (setq k (atof (dl:get "klim")))
  (if (<= k 0.0) (setq k 500.0))
  (if (= (dl:get "mon") "1") k (/ k 1000.0)))

;; σπάσιμο μεγάλου string σε κωδικούς 3/1 για entmake MTEXT
(defun dl:mt-codes (s / res n p)
  (setq res nil)
  (while (> (strlen s) 250)
    (setq n 240)
    (setq p n)
    (while (and (> p 100) (/= (substr s p 1) " ")) (setq p (1- p)))
    (if (<= p 100) (setq p n))
    (setq res (cons (cons 3 (substr s 1 p)) res))
    (setq s (substr s (1+ p))))
  (setq res (cons (cons 1 s) res))
  (reverse res))

;; εναλλακτική δημιουργία MTEXT μέσω ActiveX, αν αποτύχει το entmake
(defun dl:mt-vla (ip th wd body lay / doc sp o)
  (setq doc (vla-get-ActiveDocument (vlax-get-acad-object)))
  (setq sp (if (= (getvar "CVPORT") 1) (vla-get-PaperSpace doc) (vla-get-ModelSpace doc)))
  (setq o (vla-AddMText sp (vlax-3d-point ip) wd body))
  (vla-put-Height o th)
  (vla-put-Layer o lay)
  (vl-catch-all-apply (function vla-put-StyleName) (list o "BRB_GR"))
  (vl-catch-all-apply (function vla-put-AttachmentPoint) (list o 1))
  (vl-catch-all-apply (function vla-put-InsertionPoint) (list o (vlax-3d-point ip)))
  (vlax-vla-object->ename o))

(defun dl:count-P (s / p n)
  (setq p 0 n 0)
  (while (setq p (vl-string-search "\\P" s p)) (setq n (1+ n) p (+ p 2)))
  n)

;; κάτω άκρο του MTEXT: bounding box, αλλιώς εκτίμηση από το μήκος
(defun dl:mt-bottom (e ip th wd body / r mn mx)
  (setq r (vl-catch-all-apply
            (function (lambda ()
              (vla-getboundingbox (vlax-ename->vla-object e) (quote mn) (quote mx))
              (cadr (vlax-safearray->list mn))))))
  (if (or (null e) (vl-catch-all-error-p r) (not (numberp r)))
    (- (cadr ip) (* th 1.67 (+ 1 (dl:count-P body) (fix (/ (* (strlen body) th 0.55) wd)))))
    r))

(defun dl:block (pt title body lay / th wd e ip x1 y1 x2 y2 pad hh)
  (setq th (* (atof (dl:get "hmm")) (dl:sc)))
  (setq wd (* (atof (dl:get "wmm")) (dl:sc)))
  (setq pad (* 0.6 th) hh (* 1.15 th))
  (dl:style) (dl:layer lay 7)
  ;; κυρίως κείμενο
  (setq ip (list (car pt) (- (cadr pt) (* 2.2 hh)) 0.0))
  (if (entmake (append
    (list (cons 0 "MTEXT") (cons 100 "AcDbEntity") (cons 8 lay)
          (cons 100 "AcDbMText")
          (cons 10 ip)
          (cons 40 th) (cons 41 wd) (cons 71 1) (cons 72 5)
          (cons 7 "BRB_GR"))
    (dl:mt-codes body)))
    (setq e (entlast))
    (setq e (dl:mt-vla ip th wd body lay)))
  (setq x1 (- (car pt) pad)
        x2 (+ (car pt) wd pad)
        y1 (- (dl:mt-bottom e ip th wd body) pad)
        y2 (cadr pt))
  ;; πλαίσιο
  (entmake (list (cons 0 "LWPOLYLINE") (cons 100 "AcDbEntity") (cons 8 lay)
                 (cons 100 "AcDbPolyline") (cons 90 4) (cons 70 1)
                 (cons 10 (list x1 y1)) (cons 10 (list x2 y1))
                 (cons 10 (list x2 y2)) (cons 10 (list x1 y2))))
  ;; γραμμή τίτλου
  (entmake (list (cons 0 "LWPOLYLINE") (cons 100 "AcDbEntity") (cons 8 lay)
                 (cons 100 "AcDbPolyline") (cons 90 2) (cons 70 0)
                 (cons 10 (list x1 (- y2 (* 1.9 hh))))
                 (cons 10 (list x2 (- y2 (* 1.9 hh))))))
  ;; τίτλος
  (entmake (list (cons 0 "TEXT") (cons 100 "AcDbEntity") (cons 8 lay)
                 (cons 100 "AcDbText") (cons 7 "BRB_GR")
                 (cons 10 (list (/ (+ x1 x2) 2.0) (- y2 (* 1.45 hh)) 0.0))
                 (cons 11 (list (/ (+ x1 x2) 2.0) (- y2 (* 1.45 hh)) 0.0))
                 (cons 40 (* 1.15 th)) (cons 1 title) (cons 72 1) (cons 73 2)
                 (cons 100 "AcDbText")))
  (list x1 y1 x2 y2))

(defun dl:sign (pt lay who / th)
  (setq th (* (atof (dl:get "hmm")) (dl:sc)))
  (dl:layer lay 7)
  (entmake (list (cons 0 "MTEXT") (cons 100 "AcDbEntity") (cons 8 lay)
                 (cons 100 "AcDbMText") (cons 10 pt) (cons 40 th)
                 (cons 41 (* (atof (dl:get "wmm")) (dl:sc))) (cons 71 1) (cons 72 5)
                 (cons 7 "BRB_GR") (cons 1 who)))
  (princ))

;; ---------------- εντολές ----------------
(defun c:DILOSI ( / res pt th gap box lay *error* oldecho)
  (defun *error* (msg)
    (if oldecho (setvar "CMDECHO" oldecho))
    (if (not (member msg (list "Function cancelled" "quit / exit abort" "console break")))
      (princ (strcat "\nDILOSI - \\U+03C3\\U+03C6\\U+03AC\\U+03BB\\U+03BC\\U+03B1: " msg)))
    (princ))
  (setq oldecho (getvar "CMDECHO"))
  (setvar "CMDECHO" 0)
  (command "._UNDO" "_BEGIN")
  (setq res (dl:dialog))
  (if (= res 1)
    (progn
      (setq pt (getpoint "\n\\U+03A3\\U+03B7\\U+03BC\\U+03B5\\U+03AF\\U+03BF \\U+03B5\\U+03B9\\U+03C3\\U+03B1\\U+03B3\\U+03C9\\U+03B3\\U+03AE\\U+03C2 (\\U+03C0\\U+03AC\\U+03BD\\U+03C9-\\U+03B1\\U+03C1\\U+03B9\\U+03C3\\U+03C4\\U+03B5\\U+03C1\\U+03AC): "))
      (if pt
        (progn
          (setq lay (dl:layer "BRB_DILOSEIS" 7))
          (setq th (* (atof (dl:get "hmm")) (dl:sc)))
          (setq gap (* 3.0 th))
          (if (= (dl:get "d651") "1")
            (progn
              (setq box (dl:block pt
                "\\U+0394\\U+0397\\U+039B\\U+03A9\\U+03A3\\U+0397 \\U+039D.651/77 & \\U+039D.1337/83"
                (strcat (dl:txt-651) "\\P\\P"
                  "\\U+0397\\U+03BC\\U+03B5\\U+03C1\\U+03BF\\U+03BC\\U+03B7\\U+03BD\\U+03AF\\U+03B1: " (dl:get "hmer") "\\P"
                  "\\U+039F \\U+03A3\\U+03A5\\U+039D\\U+03A4\\U+0391\\U+039E\\U+0391\\U+03A3 \\U+039C\\U+0397\\U+03A7\\U+0391\\U+039D\\U+0399\\U+039A\\U+039F\\U+03A3" "\\P\\P\\P"
                  (dl:get "mix")
                  (if (dl:nz (dl:get "eid")) (strcat "\\P" (dl:get "eid")) "")
                  (if (dl:nz (dl:get "tee")) (strcat "\\P" "\\U+0391.\\U+039C. \\U+03A4.\\U+0395.\\U+0395. " (dl:get "tee")) ""))
                lay))
              (setq pt (list (car pt) (- (cadr box) gap) 0.0))))
          (if (= (dl:get "d4030") "1")
            (progn
              (setq box (dl:block pt
                "\\U+0394\\U+0397\\U+039B\\U+03A9\\U+03A3\\U+0397 \\U+0399\\U+0394\\U+0399\\U+039F\\U+039A\\U+03A4\\U+0397\\U+03A4\\U+0397 - \\U+0391\\U+03A1\\U+0398\\U+03A1\\U+039F 25 \\U+039D.4030/2011"
                (strcat (dl:txt-4030) "\\P\\P"
                  "\\U+0397\\U+03BC\\U+03B5\\U+03C1\\U+03BF\\U+03BC\\U+03B7\\U+03BD\\U+03AF\\U+03B1: " (dl:get "hmer") "\\P"
                  "\\U+039F/\\U+0397 \\U+0394\\U+0397\\U+039B\\U+03A9\\U+039D/\\U+039F\\U+03A5\\U+03A3\\U+0391 \\U+0399\\U+0394\\U+0399\\U+039F\\U+039A\\U+03A4\\U+0397\\U+03A4\\U+0397\\U+03A3" "\\P\\P\\P"
                  (dl:get "idio"))
                lay))))
          (princ "\n\\U+039F\\U+03B9 \\U+03B4\\U+03B7\\U+03BB\\U+03CE\\U+03C3\\U+03B5\\U+03B9\\U+03C2 \\U+03B5\\U+03B9\\U+03C3\\U+03AE\\U+03C7\\U+03B8\\U+03B7\\U+03C3\\U+03B1\\U+03BD."))
        (princ "\n\\U+0391\\U+03BA\\U+03C5\\U+03C1\\U+03CE\\U+03B8\\U+03B7\\U+03BA\\U+03B5.")))
    (princ "\n\\U+0391\\U+03BA\\U+03C5\\U+03C1\\U+03CE\\U+03B8\\U+03B7\\U+03BA\\U+03B5."))
  (command "._UNDO" "_END")
  (setvar "CMDECHO" oldecho)
  (princ))

(defun c:DILOSI4030 ( / )
  (dl:init) (dl:set "d651" "0") (dl:set "d4030" "1") (c:DILOSI))

(defun c:DILOSISET ( / v)
  (dl:init)
  (setq v (getstring (strcat "\n\\U+039A\\U+03BB\\U+03AF\\U+03BC\\U+03B1\\U+03BA\\U+03B1 1:" " <" (dl:get "klim") ">: ")))
  (if (/= v "") (dl:set "klim" v))
  (setq v (getstring (strcat "\n\\U+03A5\\U+03C8\\U+03BF\\U+03C2 \\U+03B3\\U+03C1\\U+03B1\\U+03BC\\U+03BC\\U+03AC\\U+03C4\\U+03C9\\U+03BD \\U+03C3\\U+03B5 mm \\U+03C7\\U+03B1\\U+03C1\\U+03C4\\U+03B9\\U+03BF\\U+03CD" " <" (dl:get "hmm") ">: ")))
  (if (/= v "") (dl:set "hmm" v))
  (setq v (getstring (strcat "\n\\U+03A0\\U+03BB\\U+03AC\\U+03C4\\U+03BF\\U+03C2 \\U+03C0\\U+03BB\\U+03B1\\U+03B9\\U+03C3\\U+03AF\\U+03BF\\U+03C5 \\U+03C3\\U+03B5 mm" " <" (dl:get "wmm") ">: ")))
  (if (/= v "") (dl:set "wmm" v))
  (setq v (getstring (strcat "\nLayer \\U+03B9\\U+03B4\\U+03B9\\U+03BF\\U+03BA\\U+03C4\\U+03B7\\U+03C3\\U+03AF\\U+03B1\\U+03C2" " <" *DL-LAYER* ">: ")))
  (if (/= v "") (setq *DL-LAYER* v))
  (princ "\n\\U+039F\\U+039A.")
  (princ))

(princ "\nHEXIS DILOSI v1.2 \\U+03C6\\U+03BF\\U+03C1\\U+03C4\\U+03CE\\U+03B8\\U+03B7\\U+03BA\\U+03B5. \\U+0395\\U+03BD\\U+03C4\\U+03BF\\U+03BB\\U+03AD\\U+03C2: DILOSI | DILOSI4030 | DILOSISET")
(princ)
